--/*******************************************************************************
--Copyright (C) Autelan Technology


--This software file is owned and distributed by Autelan Technology 
--********************************************************************************


--THIS SOFTWARE IS PROVIDED BY THE COPYRIGHT HOLDERS AND CONTRIBUTORS "AS IS" AND 
--ANY EXPRESS OR IMPLIED WARRANTIES, INCLUDING, BUT NOT LIMITED TO, THE IMPLIED 
--WARRANTIES OF MERCHANTABILITY AND FITNESS FOR A PARTICULAR PURPOSE ARE 
--DISCLAIMED. IN NO EVENT SHALL THE COPYRIGHT OWNER OR CONTRIBUTORS BE LIABLE FOR 
--ANY DIRECT, INDIRECT, INCIDENTAL, SPECIAL, EXEMPLARY, OR CONSEQUENTIAL DAMAGES 
--(INCLUDING, BUT NOT LIMITED TO, PROCUREMENT OF SUBSTITUTE GOODS OR SERVICES; 
--LOSS OF USE, DATA, OR PROFITS; OR BUSINESS INTERRUPTION) HOWEVER CAUSED AND ON 
--ANY THEORY OF LIABILITY, WHETHER IN CONTRACT, STRICT LIABILITY, OR TORT 
--(INCLUDING NEGLIGENCE OR OTHERWISE) ARISING IN ANY WAY OUT OF THE USE OF THIS 
--SOFTWARE, EVEN IF ADVISED OF THE POSSIBILITY OF SUCH DAMAGE.
--********************************************************************************
--* dot11-ac-mib
--*
--*
--* CREATOR:
--* autelan.software.Network Dep. team
--*
--* DESCRIPTION:
--* ac infomation mibs.
--*
--*
--*******************************************************************************/

DOT11-AC-MIB DEFINITIONS ::= BEGIN
IMPORTS

	dot11-wireless
			FROM DOT11-GROUP-SMI
   	PhysAddress, 
--	TEXTUAL-CONVENTION, 
	TruthValue,
--   	NOTIFICATION-GROUP, 
--	OBJECT-GROUP, 
--	MODULE-COMPLIANCE
--       			FROM SNMPv2-CONF
        MacAddress,DisplayString,RowStatus,TAddress
				FROM SNMPv2-TC
   	MODULE-IDENTITY, 
	OBJECT-TYPE,
	NOTIFICATION-TYPE,
   	Integer32, 
--	Unsigned32, 
--	Counter32,
	TimeTicks,
	enterprises
       			FROM SNMPv2-SMI;

	InetAddressIPv6 ::= TEXTUAL-CONVENTION
	DISPLAY-HINT "2x:"
     	STATUS       current
     	DESCRIPTION "This data type is used to model IPv6 addresses. This is a binary string of 16 octets in networkbyte-order."
	SYNTAX       OCTET STRING (SIZE (50))

dot11AcGroup MODULE-IDENTITY
    LAST-UPDATED "201311280000Z"        -- Nov 28th 2013
    ORGANIZATION " AuteLan Network Management Working Group
                  http://www.autelan.com"
    CONTACT-INFO
        "General Discussion: support@autelan.com
         To Subscribe: http://www.autelan.com

         Liu Tao
         AuteLan Technology Ltd.,NO.1 Agricultural University Sourth Street,
Haidian

         District,Beijing,China(100084)
         Email:  liutao@autelan.com

         Wang Peng
         AuteLan Technology Ltd.,NO.1 Agricultural University Sourth Street,
Haidian

         District,Beijing,China(100084)
         Email: wangpeng@autelan.com

	 Tang Siqi
         AuteLan Technology Ltd.,NO.1 Agricultural University Sourth Street,
Haidian

         District,Beijing,China(100084)
         Email: tangsq@autelan.com"


    DESCRIPTION
        "Copyright (C) 2009 The Internet Society.  This version of
         the MIB module is part of RFC xxx; see the RFC itself
         for full legal notices.

         This MIB module contains managed object definitions for
         the AuteLan Protocol."
    REVISION    "201311280000Z"
    DESCRIPTION
        "Initial version published as RFC xxx"
         ::= { 	dot11-wireless 2 }
         
--fist path


-- **********************************************************************
-- * dot11AcInfo
-- **********************************************************************
dot11AcGeneralInfo 	OBJECT IDENTIFIER ::={ dot11AcGroup 1}
dot11AcInfo 		OBJECT IDENTIFIER ::={ dot11AcGeneralInfo 1 }
acSoftwareName 			OBJECT-TYPE
				SYNTAX		DisplayString
				MAX-ACCESS 	read-only
				STATUS		current
				DESCRIPTION
					"AC system software name."
				::={ dot11AcInfo 1 }

acSoftwareVersion 		OBJECT-TYPE
				SYNTAX		DisplayString
				MAX-ACCESS 	read-only
				STATUS		current
				DESCRIPTION
					"AC system software version."
				::={ dot11AcInfo 2 }

acRunningTime 			OBJECT-TYPE
				SYNTAX  TimeTicks
				MAX-ACCESS  read-only
				STATUS  current
				DESCRIPTION
					"AC runtime. "
				::= { dot11AcInfo  3 }

acSampleTime			OBJECT-TYPE
				SYNTAX  Integer32
				MAX-ACCESS  read-write
				STATUS  current
				DESCRIPTION
					"AC sample time. "
				::= { dot11AcInfo  4 }

acSystemTime			OBJECT-TYPE
				SYNTAX		DisplayString
				MAX-ACCESS 	read-write
				STATUS		current
				DESCRIPTION
					"AC system time,the time format is YYYY-MM-DD HH:MM:SS.If the input format didn't match this format,the time will not be set"
				::={ dot11AcInfo  5 }

acSoftwareVendor 		OBJECT-TYPE
				SYNTAX		DisplayString
				MAX-ACCESS 	read-only
				STATUS		current
				DESCRIPTION
					"AC system software productor."
				::={ dot11AcInfo  6 }

acContactInfo	 		OBJECT-TYPE
				SYNTAX		DisplayString
				MAX-ACCESS 	read-write
				STATUS		current
				DESCRIPTION
					"AC contact information(Include phone number and contact name)."
				::={ dot11AcInfo  7 }

acProductName 			OBJECT-TYPE
				SYNTAX   OCTET  STRING(SIZE(0..32))
				MAX-ACCESS  read-only
				STATUS  current
				DESCRIPTION
					"AC Product Name."
				::= { dot11AcInfo  8 }

acLocationInfo  		OBJECT-TYPE
				SYNTAX 		DisplayString
				MAX-ACCESS  read-write
				STATUS  current
				DESCRIPTION
					"AC location information. "
				::= {dot11AcInfo  9 }

acDomain	     		OBJECT-TYPE
				SYNTAX   	DisplayString
				MAX-ACCESS  	read-only
				STATUS  	current
				DESCRIPTION
					"The country or district the device support. "
				::= { dot11AcInfo  10 }

acLatestPollDevTime	    	OBJECT-TYPE
				SYNTAX   DisplayString
				MAX-ACCESS  read-write
				STATUS  current
				DESCRIPTION
					"The latest update device information. "
				::= { dot11AcInfo  11 }

acLogServerAddr		   	OBJECT-TYPE
				SYNTAX   	IpAddress
				MAX-ACCESS  	read-write
				STATUS  	current
				DESCRIPTION
					"Log server address. "
				::= { dot11AcInfo  12 }

acSyslogServerPort		OBJECT-TYPE
				SYNTAX		INTEGER
				MAX-ACCESS  	read-write
				STATUS  	current
				DESCRIPTION
					"System log server port number."
				::= { dot11AcInfo  13 }

acNTPConfig	    		OBJECT-TYPE
				SYNTAX    IpAddress
				MAX-ACCESS  read-write
				STATUS  current
				DESCRIPTION
					"NTP server configration (IP or domain name)."
				::= { dot11AcInfo  14 }

acTimeAfterNTPCal		OBJECT-TYPE
				SYNTAX    INTEGER
				MAX-ACCESS  read-only
				STATUS  current
				DESCRIPTION
					"The connect Time that after NTP regulated."
				::= { dot11AcInfo  15 }

acSTP 	  	  		OBJECT-TYPE
				SYNTAX    INTEGER{
						open(1),
						close(0)
						}
				MAX-ACCESS  read-write
				STATUS  current
				DESCRIPTION
					"Spanning-tree protocol(RSTP)."
				::= { dot11AcInfo  16 }

acSnmpTrapConfig  		OBJECT-TYPE
				SYNTAX    DisplayString
				MAX-ACCESS  read-write
				STATUS  current
				DESCRIPTION
					"Set the trap type of Trap host,the definition of community list."
				::= { dot11AcInfo  17 }

acStatWindowTime		OBJECT-TYPE
				SYNTAX    INTEGER
				MAX-ACCESS  read-write
				STATUS  current
				DESCRIPTION
					"Sliding window length of time statistics."
				::= { dot11AcInfo  18 }

acHeartbeatPeriod		OBJECT-TYPE
				SYNTAX    INTEGER(0..3600)
				MAX-ACCESS  read-write
				STATUS  current
				DESCRIPTION
					"Alarm reporting channel heartbeat detection cycle."
				::= { dot11AcInfo  19 }

acSysRestart			OBJECT-TYPE
				SYNTAX    INTEGER{
                                                Normal(1),
						Restart(2)
						}
				MAX-ACCESS  read-write
				STATUS  current
				DESCRIPTION
					"If config this parameter,the system will restart."
				::= { dot11AcInfo  20 }

acSysReset			OBJECT-TYPE
				SYNTAX    INTEGER{
                                                Normal(1),
						Reset(2)
						}
				MAX-ACCESS  read-write
				STATUS  current
				DESCRIPTION
					"If config this parameter,the system will restore factory settings."
				::= { dot11AcInfo  21 }
				
TimeSynPeriod			OBJECT-TYPE
				SYNTAX    INTEGER(1..31)
				MAX-ACCESS  read-write
				STATUS  current
				DESCRIPTION
					"Time Synchronization period (Days)"
				::= { dot11AcInfo  22 }		
				
SyslogSvcEnable			OBJECT-TYPE
				SYNTAX    TruthValue
				MAX-ACCESS  read-write
				STATUS  current
				DESCRIPTION
					"Whether to open Syslog Service."
				::= { dot11AcInfo  23 }	
				
SyslogReportEventLevel		OBJECT-TYPE
				SYNTAX    INTEGER{
						 Information(1),
						 Notice(2),
						 Warning(3),
						 Error(4),
						 Critical(5),
						 Debug(6)
						 
						 }
				MAX-ACCESS  read-write
				STATUS  current
				DESCRIPTION
					"Syslog Report Event Level."
				::= { dot11AcInfo  24 }	
				
SysObjectId			OBJECT-TYPE
				SYNTAX    DisplayString
				MAX-ACCESS  read-only
				STATUS  current
				DESCRIPTION
					"System Object ID."
				::= { dot11AcInfo  25 }	

acHeartBeatEnable		OBJECT-TYPE
				SYNTAX    INTEGER{
                                                disable(0),
						enable(1)
						}
				MAX-ACCESS  read-write
				STATUS  current
				DESCRIPTION
					"System HeartBeatEnable ."
				::= { dot11AcInfo  26 }	

NormalCollectCycle             OBJECT-TYPE
				SYNTAX      Integer32
				MAX-ACCESS  read-write
				STATUS  current
				DESCRIPTION
					"NormalCollectCycle ."
				::= { dot11AcInfo  27}

RtCollectCycle                  OBJECT-TYPE
				SYNTAX      Integer32(2..5)
				MAX-ACCESS  read-write
				STATUS  current
				DESCRIPTION
					"RtCollectCycle ."
				::= { dot11AcInfo  28}	
					
acSoftwareHwspecr                  OBJECT-TYPE
				SYNTAX      DisplayString
				MAX-ACCESS  read-only
				STATUS  current
				DESCRIPTION
					"acsoftware and hareware Information ."
				::= { dot11AcInfo  29}
																		
acSoftwareBigVersion 		OBJECT-TYPE
				SYNTAX		DisplayString
				MAX-ACCESS 	read-only
				STATUS		current
				DESCRIPTION
					"AC system software big version."
				::={ dot11AcInfo 33 }
				
acBootImg			OBJECT-TYPE
				SYNTAX		DisplayString
				MAX-ACCESS 	read-write
				STATUS		current
				DESCRIPTION
					"AC boot img infomation."
				::={ dot11AcInfo 34 }				

acWriteConfig			OBJECT-TYPE
				SYNTAX		DisplayString
				MAX-ACCESS 	read-write
				STATUS		current
				DESCRIPTION
					"Show the config name and write the config(1)  "
				::={ dot11AcInfo 35 }
				
sysBackupIdentity			OBJECT-TYPE
				SYNTAX		Integer32{
							 NULL(0),
							 Slave(1),
							 Master(2)
							}
				MAX-ACCESS 	read-only
				STATUS		current
				DESCRIPTION
					"Show the AC  backup identity "
				::={ dot11AcInfo 36 }
				
sysBackupMode				OBJECT-TYPE
				SYNTAX		Integer32{
							 NULL(0),
							 Cold-Backup(1),
							 Hot-Backup(2)
							}
				MAX-ACCESS 	read-only
				STATUS		current
				DESCRIPTION
					"Show the AC  backup mode "
				::={ dot11AcInfo 37 }

sysBackupStatus				OBJECT-TYPE
				SYNTAX		Integer32{
							 NULL(0),
							 Standby(1),
							 Active(2)
							}
				MAX-ACCESS 	read-only
				STATUS		current
				DESCRIPTION
					"Show the AC  backup status "
				::={ dot11AcInfo 38 }

sysBackupNetworManageIp		OBJECT-TYPE
				SYNTAX		IpAddress
				MAX-ACCESS 	read-only
				STATUS		current
				DESCRIPTION
					"Show the AC  backup networkManage IpAddress "
				::={ dot11AcInfo 39 }

sysBackupSwitchTimes         	OBJECT-TYPE
                                SYNTAX          Counter32
                                MAX-ACCESS      read-only
                                STATUS          current
                                DESCRIPTION
                                        "switch times of vrrp hansi status"
                                ::={ dot11AcInfo 40 }
sysBackupNetworManageIpv6	OBJECT-TYPE
				SYNTAX		InetAddressIPv6
				MAX-ACCESS 	read-only
				STATUS		current
				DESCRIPTION
					"Show the AC  backup networkManage IPV6Address "
				::={ dot11AcInfo 41 }

acslotinfo			OBJECT-TYPE
				SYNTAX		DisplayString
				MAX-ACCESS 	read-only
				STATUS		current
				DESCRIPTION
					"Show the ac slot info  "
				::={ dot11AcInfo 42 }

dot11AcDeviceInfo	OBJECT IDENTIFIER ::={ dot11AcGeneralInfo 2 }
acDeviceName	  		OBJECT-TYPE
				SYNTAX   DisplayString
				MAX-ACCESS  read-write
				STATUS  current
				DESCRIPTION
					"The device name."
				::= { dot11AcDeviceInfo  1 }

acManufacturers  		OBJECT-TYPE
				SYNTAX   OCTET  STRING(SIZE(0..32))
				MAX-ACCESS  read-only
				STATUS  current
				DESCRIPTION
					"The manufacturer of the product."
				::= { dot11AcDeviceInfo  2 }

acDeviceSN	 		OBJECT-TYPE
				SYNTAX		DisplayString
				MAX-ACCESS 	read-only
				STATUS		current
				DESCRIPTION
					"Device SN."
				::={ dot11AcDeviceInfo 3 }

acDeviceType			OBJECT-TYPE
				SYNTAX		DisplayString
				MAX-ACCESS 	read-only
				STATUS		current
				DESCRIPTION
					"Device type."
				::={ dot11AcDeviceInfo 4 }


acDeviceHWVersion		OBJECT-TYPE
				SYNTAX		DisplayString
				MAX-ACCESS 	read-only
				STATUS		current
				DESCRIPTION
					"Device hardware version."
				::={ dot11AcDeviceInfo 5 }

acMemoryType			OBJECT-TYPE
				SYNTAX    DisplayString
				MAX-ACCESS  read-only
				STATUS  current
				DESCRIPTION
					"Memory type."
				::= { dot11AcDeviceInfo  6 }
				
acMemoryCapacity    		OBJECT-TYPE
				SYNTAX    Gauge32
				MAX-ACCESS  read-only
				STATUS  current
				DESCRIPTION
					"Memory capacity(Units KB)."
				::= { dot11AcDeviceInfo  7 }

acMemRTUsage		    	OBJECT-TYPE
				SYNTAX    INTEGER
				MAX-ACCESS  read-only
				STATUS  current
				DESCRIPTION
					"Memory current use rate."
				::= { dot11AcDeviceInfo  8 }

acMemPeakUsage			OBJECT-TYPE
				SYNTAX    INTEGER
				MAX-ACCESS  read-only
				STATUS  current
				DESCRIPTION
					"Memory peak use rate."
				::= { dot11AcDeviceInfo  9 }

acMemAvgUsage			OBJECT-TYPE
				SYNTAX    INTEGER
				MAX-ACCESS  read-only
				STATUS  current
				DESCRIPTION
					"Memory average use rate."
				::= { dot11AcDeviceInfo  10 }

acMemUsageThreshhd		OBJECT-TYPE
				SYNTAX    INTEGER
				MAX-ACCESS  read-write
				STATUS  current
				DESCRIPTION
					"If memory use rate highter than this value ,send trap(While setting value,just input numbers)."
				::= { dot11AcDeviceInfo  11 }

acCPUType			OBJECT-TYPE
				SYNTAX    DisplayString
				MAX-ACCESS  read-only
				STATUS  current
				DESCRIPTION
					"CPU type."
				::= { dot11AcDeviceInfo  12 }

acCPURTUsage		    	OBJECT-TYPE
				SYNTAX    INTEGER
				MAX-ACCESS  read-only
				STATUS  current
				DESCRIPTION
					"CPU current use rate."
				::= { dot11AcDeviceInfo  13 }

acCPUPeakUsage			OBJECT-TYPE
				SYNTAX    DisplayString
				MAX-ACCESS  read-only
				STATUS  current
				DESCRIPTION
					"CPU peak use rate."
				::= { dot11AcDeviceInfo  14 }

acCPUAvgUsage			OBJECT-TYPE
				SYNTAX    INTEGER
				MAX-ACCESS  read-only
				STATUS  current
				DESCRIPTION
					"CPU average use rate."
				::= { dot11AcDeviceInfo  15 }

acCPUusageThreshhd		OBJECT-TYPE
				SYNTAX    INTEGER
				MAX-ACCESS  read-write
				STATUS  current
				DESCRIPTION
					"If CPU use rate highter than this value ,send trap."
				::= { dot11AcDeviceInfo  16 }

acFlashType		    	OBJECT-TYPE
				SYNTAX    DisplayString
				MAX-ACCESS  read-only
				STATUS  current
				DESCRIPTION
					"Flash Type."
				::= { dot11AcDeviceInfo  17 }

acFlashCapacity		    	OBJECT-TYPE
				SYNTAX    Gauge32
				MAX-ACCESS  read-only
				STATUS  current
				DESCRIPTION
					"Flash capacity(Units KB)."
				::= { dot11AcDeviceInfo  18 }

acFlashResidualSpace 	    	OBJECT-TYPE
				SYNTAX    DisplayString
				MAX-ACCESS  read-only
				STATUS  current
				DESCRIPTION
					"Flash residual space(Units KB)."
				::= { dot11AcDeviceInfo  19 }

acWorkTemperature 	    	OBJECT-TYPE
				SYNTAX    DisplayString
				MAX-ACCESS  read-only
				STATUS  current
				DESCRIPTION
					"Work Temperature."
				::= { dot11AcDeviceInfo  20 }

acWtpCPUusageThreshhd	    	OBJECT-TYPE
				SYNTAX    INTEGER
				MAX-ACCESS  read-write
				STATUS  current
				DESCRIPTION
					"acWtpCPUusageThreshhd."
				::= { dot11AcDeviceInfo  21 }

acWtpMemusageThreshhd	    	OBJECT-TYPE
				SYNTAX    INTEGER
				MAX-ACCESS  read-write
				STATUS  current
				DESCRIPTION
					"acWtpMemusageThreshhd."
				::= { dot11AcDeviceInfo  22 }
				
acCPUFrequency	 	    	OBJECT-TYPE
				SYNTAX    DisplayString
				MAX-ACCESS  read-only
				STATUS  current
				DESCRIPTION
					"acCPUFrequency."
				::= { dot11AcDeviceInfo  24 }				

-- **********************************************************************
-- * dot11AcPara
-- **********************************************************************

dot11AcPara 	OBJECT IDENTIFIER ::={ dot11AcGroup 2}

acIpAddress  			OBJECT-TYPE
				SYNTAX   IpAddress
				MAX-ACCESS  read-only
				STATUS  current
				DESCRIPTION
					"AC IP address . "
				::= { dot11AcPara  1}

acNetMask  			OBJECT-TYPE
				SYNTAX     IpAddress
				MAX-ACCESS  read-only
				STATUS  current
				DESCRIPTION
					"AC IP address mask."
				::= { dot11AcPara  2}

acNetElementCode   		OBJECT-TYPE
				SYNTAX	DisplayString
				MAX-ACCESS  read-write
				STATUS  current
				DESCRIPTION
					"AC network element coding."
				::= { dot11AcPara  3}

acAuthenMothedsupp 		OBJECT-TYPE
				SYNTAX		INTEGER{
							EAP-SIM(1),
							WEB(2),
							EPA-MD5(3),
							ALL(4)
							}
				MAX-ACCESS 	read-only
				STATUS		current
				DESCRIPTION
					"Support EAP-SIM,WEB,EAP-MD5 certification."
				::={  dot11AcPara 4 }

acMacAddress    		OBJECT-TYPE
				SYNTAX  PhysAddress
				MAX-ACCESS  read-only
				STATUS  current
				DESCRIPTION
					"AC mac address. "
				::= { dot11AcPara  5}

acConPortalURL	 		OBJECT-TYPE
				SYNTAX		DisplayString
				MAX-ACCESS 	read-write
				STATUS		current
				DESCRIPTION
					"Portal server URL."
				::={  dot11AcPara 6 }

acPortalServerPort 		OBJECT-TYPE
				SYNTAX		INTEGER
				MAX-ACCESS 	read-write
				STATUS		current
				DESCRIPTION
					"Portal server port."
				::={  dot11AcPara 7 }

acMaxPortalOnlineUsers		OBJECT-TYPE
				SYNTAX		INTEGER
				MAX-ACCESS 	read-only
				STATUS		current
				DESCRIPTION
					"The max number that portal server can login."
				::={  dot11AcPara 8 }

acPortalOnlineUsers		OBJECT-TYPE
				SYNTAX		INTEGER
				MAX-ACCESS 	read-only
				STATUS		current
				DESCRIPTION
					"The max number that portal server online user."
				::={  dot11AcPara 9 }

acMaxPPPoEOnlineUsers		OBJECT-TYPE
				SYNTAX		INTEGER
				MAX-ACCESS 	read-only
				STATUS		current
				DESCRIPTION
					"Max PPPoE online user number."
				::={  dot11AcPara 10 }

acPPPoEOnlineUsers		OBJECT-TYPE
				SYNTAX		INTEGER
				MAX-ACCESS 	read-only
				STATUS		current
				DESCRIPTION
					"PPPoE online user number."
				::={  dot11AcPara 11 }

acCertifServerType 		OBJECT-TYPE
				SYNTAX		DisplayString
				MAX-ACCESS 	read-only
				STATUS		current
				DESCRIPTION
					"AS certificate server type."
				::={  dot11AcPara 12 }

acConASServerIP 		OBJECT-TYPE
				SYNTAX		IpAddress
				MAX-ACCESS 	read-write
				STATUS		current
				DESCRIPTION
					"Connected AS IP address."
				::={  dot11AcPara 13 }

acFirstConDNSServer 		OBJECT-TYPE
				SYNTAX		IpAddress
				MAX-ACCESS 	read-write
				STATUS		current
				DESCRIPTION
					"First DNS Server IP address."
				::={  dot11AcPara 14 }

acSeconConDNSServer 		OBJECT-TYPE
				SYNTAX		IpAddress
				MAX-ACCESS 	read-write
				STATUS		current
				DESCRIPTION
					"Secondary DNS Server IP address."
				::={  dot11AcPara 15 }

acTrapDesIPAddress 		OBJECT-TYPE
				SYNTAX		DisplayString
				MAX-ACCESS 	read-write
				STATUS		current
				DESCRIPTION
					"The target IP of net-management broadcast information（AC）."
				::={  dot11AcPara 16 }

acSNMPPort	 		OBJECT-TYPE
				SYNTAX		INTEGER 
				MAX-ACCESS 	read-only
				STATUS		current
				DESCRIPTION
					"SNMP port number."
				::={  dot11AcPara 17 }
				
SysGWAddr	 		OBJECT-TYPE
				SYNTAX		IpAddress
				MAX-ACCESS 	read-write
				STATUS		current
				DESCRIPTION
					"AC Gateway address."
				::={  dot11AcPara 18 }	

acTrapPort	 		OBJECT-TYPE
				SYNTAX		INTEGER
				MAX-ACCESS 	read-only
				STATUS		current
				DESCRIPTION
					"AC Trap Port."
				::={  dot11AcPara 19 }
				
acIpv6Address  			OBJECT-TYPE
				SYNTAX   InetAddressIPv6
				MAX-ACCESS  read-only
				STATUS  current
				DESCRIPTION
					"AC IPv6 address . "
				::= { dot11AcPara  20}	
acIpv6Prefix  			OBJECT-TYPE
				SYNTAX   DisplayString
				MAX-ACCESS  read-only
				STATUS  current
				DESCRIPTION
					"AC IPv6 address prefix . "
				::= { dot11AcPara  21}	
acIpv6type  			OBJECT-TYPE
				SYNTAX   DisplayString
				MAX-ACCESS  read-only
				STATUS  current
				DESCRIPTION
					"AC IPv6 address type. "
				::= { dot11AcPara  22}			
-- **********************************************************************
-- * dot11AcStats
-- **********************************************************************
dot11AcStatistics OBJECT IDENTIFIER ::={ dot11AcGroup 3}
dot11AcStats  OBJECT IDENTIFIER ::={ dot11AcStatistics 1 }
dot11AcStorageInfo  OBJECT IDENTIFIER ::={ dot11AcStatistics 2 }
acNumAPInAC 			OBJECT-TYPE
				SYNTAX		INTEGER
				MAX-ACCESS 	read-only
				STATUS		current
				DESCRIPTION
					"The total number of AP which connect with AC."
				::={ dot11AcStats 1 }

acOnlineNumAPInAC		OBJECT-TYPE
				SYNTAX		INTEGER
				MAX-ACCESS 	read-only
				STATUS		current
				DESCRIPTION
					"The total number of online AP which connect with AC."
				::={ dot11AcStats 2 }


acUsersonAC 			OBJECT-TYPE
				SYNTAX		INTEGER
				MAX-ACCESS 	read-only
				STATUS		current
				DESCRIPTION
					"The online user number."
				::={ dot11AcStats 3 }
				
acUplinkDataThroughput    	OBJECT-TYPE
				SYNTAX   Counter64
				MAX-ACCESS  read-only
				STATUS  current
				DESCRIPTION
					"The uplink traffic. "
				::= { dot11AcStats  4}
				
acDownlinkDataThroughput   	OBJECT-TYPE
				SYNTAX   Counter64
				MAX-ACCESS  read-only
				STATUS  current
				DESCRIPTION
					"The downlink traffic. "
				::= { dot11AcStats  5 }

acPortThroughput    		OBJECT-TYPE
				SYNTAX    Counter64
				MAX-ACCESS  read-only
				STATUS  current
				DESCRIPTION
					" Port throughput."
				::= {  dot11AcStats  6 }

acInACRoamingSuccRate		OBJECT-TYPE
				SYNTAX    Counter32
				MAX-ACCESS  read-only
				STATUS  current
				DESCRIPTION
					"The successful number that roaming terminal in region."
				::= {  dot11AcStats  7 }

acOutACRoamingSuccRate		OBJECT-TYPE
				SYNTAX    INTEGER
				MAX-ACCESS  read-only
				STATUS  current
				DESCRIPTION
					"The successful number that roaming terminal out region."
				::= {  dot11AcStats  8 }

acAuthReqCnt			OBJECT-TYPE
				SYNTAX    Counter32
				MAX-ACCESS  read-only
				STATUS  current
				DESCRIPTION
					"The number of certification request."
				::= {  dot11AcStats  9 }

acAuthSucCnt			OBJECT-TYPE
				SYNTAX    Counter32
				MAX-ACCESS  read-only
				STATUS  current
				DESCRIPTION
					"The successful number of certification request."
				::= {  dot11AcStats  10 }

acAuthFailCnt			OBJECT-TYPE
				SYNTAX    Counter32
				MAX-ACCESS  read-only
				STATUS  current
				DESCRIPTION
					"The failed number of certification request."
				::= {  dot11AcStats  11 }

acAuthRejectCnt			OBJECT-TYPE
				SYNTAX    Counter32
				MAX-ACCESS  read-only
				STATUS  current
				DESCRIPTION
					"The rejection number of certification request."
				::= {  dot11AcStats  12 }

acAuthAttemptCnt		OBJECT-TYPE
				SYNTAX    Counter32
				MAX-ACCESS  read-only
				STATUS  current
				DESCRIPTION
					"The attempt number of certification request."
				::= {  dot11AcStats  13 }

wtpStaAllReassoc		OBJECT-TYPE
				SYNTAX    Counter32
				MAX-ACCESS  read-only
				STATUS  current
				DESCRIPTION
					"All the reassociate number of station."
				::= {  dot11AcStats  14 }

acStatus			OBJECT-TYPE
				SYNTAX    INTEGER{
						work-mode(1),
						unwork-mode(2),
						backup-mode(3)
						}
				MAX-ACCESS  read-only
				STATUS  current
				DESCRIPTION
					"AC work mode."
				::= {  dot11AcStats  15 }

acStandbySwitch			OBJECT-TYPE
				SYNTAX    INTEGER{
						not-open(1),
						primary-mode(2),
						backup-mode(3)
						}
				MAX-ACCESS  read-only
				STATUS  current
				DESCRIPTION
					"AC standby switch."
				::= {  dot11AcStats  16 }

acBandWidthAvgUtilization 	OBJECT-TYPE
				SYNTAX    INTEGER
				MAX-ACCESS  read-only
				STATUS  current
				DESCRIPTION
					"AC band width average utilization ."
				::= {  dot11AcStats  17 }

acLostPktsAvgUtilization 	OBJECT-TYPE
				SYNTAX    INTEGER
				MAX-ACCESS  read-only
				STATUS  current
				DESCRIPTION
					"AC lost packets average utilization ."
				::= {  dot11AcStats  18 }

acMaxStaNum		 	OBJECT-TYPE
				SYNTAX    Counter64
				MAX-ACCESS  read-only
				STATUS  current
				DESCRIPTION
					"AC max station mum."
				::= {  dot11AcStats  19 }

acRadiusReqSuccRate	 	OBJECT-TYPE
				SYNTAX    INTEGER
				MAX-ACCESS  read-only
				STATUS  current
				DESCRIPTION
					"Radius request successful rate."
				::= {  dot11AcStats  20 }
				
acOutACRoamingInSuccRate	OBJECT-TYPE
				SYNTAX    Counter32
				MAX-ACCESS  read-only
				STATUS  current
				DESCRIPTION
					"The successful in number that roaming terminal out region."
				::= {  dot11AcStats  21 }

acOutACRoamingOutSuccRate	OBJECT-TYPE
				SYNTAX    Counter32
				MAX-ACCESS  read-only
				STATUS  current
				DESCRIPTION
					"The successful out number that roaming terminal out region."
				::= {  dot11AcStats  22 }
				
acPortalLogoffnum		OBJECT-TYPE
				SYNTAX    Counter32
				MAX-ACCESS  read-only
				STATUS  current
				DESCRIPTION
					"The  ac portal logoff number."
				::= {  dot11AcStats  23 }

acChallengeRecReqnum	        OBJECT-TYPE
					SYNTAX     INTEGER
					MAX-ACCESS read-only
					STATUS     current
					DESCRIPTION
				        	"The ac portal receive challenge request number ."
					::= { dot11AcStats 24 }

acChallengeResReqnum	        OBJECT-TYPE
					SYNTAX     INTEGER
					MAX-ACCESS read-only
					STATUS     current
					DESCRIPTION
				        	"The ac portal response challenge request number ."
					::= { dot11AcStats 25 }

acAuthRecReqnum    	                OBJECT-TYPE
					SYNTAX     INTEGER
					MAX-ACCESS read-only
					STATUS     current
					DESCRIPTION
				        	"The ac portal receive Auth request number ."
					::= { dot11AcStats 26 }

acSendRadiusReqnum    	        OBJECT-TYPE
					SYNTAX     INTEGER
					MAX-ACCESS read-only
					STATUS     current
					DESCRIPTION
				        	"The ac portal send radius request number ."
					::= { dot11AcStats 27 }

acRecRadiusResReqnum    	        OBJECT-TYPE
					SYNTAX     Counter32
					MAX-ACCESS read-only
					STATUS     current
					DESCRIPTION
				        	"The ac portal receive radius response request number ."
					::= { dot11AcStats 28 }

acRecRadiusReqSuccnum    	        OBJECT-TYPE
					SYNTAX     INTEGER
					MAX-ACCESS read-only
					STATUS     current
					DESCRIPTION
				        	"The ac portal receive radius request success number ."
					::= { dot11AcStats 29 }

acAuthResReqnum    	                OBJECT-TYPE
					SYNTAX     INTEGER
					MAX-ACCESS read-only
					STATUS     current
					DESCRIPTION
				        	"The ac portal response Auth request number ."
					::= { dot11AcStats 30 }

acSendRadiusOfflineReqnum    	OBJECT-TYPE
					SYNTAX     INTEGER
					MAX-ACCESS read-only
					STATUS     current
					DESCRIPTION
				        	"The ac portal send radius offline request number ."
					::= { dot11AcStats 31 }

acRecRadiusOfflineResnum    	OBJECT-TYPE
					SYNTAX     INTEGER
					MAX-ACCESS read-only
					STATUS     current
					DESCRIPTION
				        	"The ac portal receive radius offline response number ."
					::= { dot11AcStats 32 }

acAcctReqnum    	                OBJECT-TYPE
					SYNTAX     INTEGER
					MAX-ACCESS read-only
					STATUS     current
					DESCRIPTION
				        	"Account request number ."
					::= { dot11AcStats 33 }

acAcctReqSuccnum    	        OBJECT-TYPE
					SYNTAX     INTEGER
					MAX-ACCESS read-only
					STATUS     current
					DESCRIPTION
				        	"Account success number ."
					::= { dot11AcStats 34 }

acLogoffRate    	                OBJECT-TYPE
					SYNTAX     INTEGER
					MAX-ACCESS read-only
					STATUS     current
					DESCRIPTION
				        	"User log off rate ."
					::= { dot11AcStats 35 }	
					
acAssociatedTotalUserNum		OBJECT-TYPE
					SYNTAX    INTEGER
					MAX-ACCESS  read-only
					STATUS  current
					DESCRIPTION
						"The total associated user numbers."
					::= {  dot11AcStats  36 }				
				

acAuthTimeoutNum    	                OBJECT-TYPE
					SYNTAX     INTEGER
					MAX-ACCESS read-only
					STATUS     current
					DESCRIPTION
				        	"Auth Timeout Number ."
					::= { dot11AcStats 37 }	

acChallengeTimeoutNum    	           OBJECT-TYPE
					SYNTAX     INTEGER
					MAX-ACCESS read-only
					STATUS     current
					DESCRIPTION
				        	"Challenge Timeout Number ."
					::= { dot11AcStats 38 }	

acChallengeRejectNum    	            OBJECT-TYPE
					SYNTAX     INTEGER
					MAX-ACCESS read-only
					STATUS     current
					DESCRIPTION
				        	"Challenge Reject Number ."
					::= { dot11AcStats 39 }	

acChallengeBusyNum    	            OBJECT-TYPE
					SYNTAX     INTEGER
					MAX-ACCESS read-only
					STATUS     current
					DESCRIPTION
				        	"Challenge Busy Number ."
					::= { dot11AcStats 40 }	

acAuthPasswordMissingNum    	            OBJECT-TYPE
					SYNTAX     INTEGER
					MAX-ACCESS read-only
					STATUS     current
					DESCRIPTION
				        	"Auth Password Missing Number ."
					::= { dot11AcStats 41 }	

acAuthUnknownTypeNum    	            OBJECT-TYPE
					SYNTAX     INTEGER
					MAX-ACCESS read-only
					STATUS     current
					DESCRIPTION
				        	"Auth Unknown Type Number ."
					::= { dot11AcStats 42 }	

acAuthBusyNum    	            OBJECT-TYPE
					SYNTAX     INTEGER
					MAX-ACCESS read-only
					STATUS     current
					DESCRIPTION
				        	"Auth Busy Number ."
					::= { dot11AcStats 43 }	

acAuthDisorderNum    	            OBJECT-TYPE
					SYNTAX     INTEGER
					MAX-ACCESS read-only
					STATUS     current
					DESCRIPTION
				        	"Auth Disorder Number ."
					::= { dot11AcStats 44 }	
					
acPortalErrcode0Num		    OBJECT-TYPE
				    SYNTAX    Counter32
				    MAX-ACCESS  read-only
				    STATUS  current
				    DESCRIPTION
					        "The ac portal number which errcode is 0."
					::= {  dot11AcStats  45 }					
					
acPortalErrcode1Num		    OBJECT-TYPE
				    SYNTAX    Counter32
				    MAX-ACCESS  read-only
				    STATUS  current
				    DESCRIPTION
					        "The ac portal number which errcode is 1."
					::= {  dot11AcStats  46 }
					
acPortalErrcode2Num		    OBJECT-TYPE
				    SYNTAX    Counter32
				    MAX-ACCESS  read-only
				    STATUS  current
				    DESCRIPTION
					        "The ac portal number which errcode is 2."
					::= {  dot11AcStats  47 }
					
acPortalErrcode3Num		    OBJECT-TYPE
				    SYNTAX    Counter32
				    MAX-ACCESS  read-only
				    STATUS  current
				    DESCRIPTION
					        "The ac portal number which errcode is 3."
					::= {  dot11AcStats  48 }
					
acPortalErrcode4Num		    OBJECT-TYPE
				    SYNTAX    Counter32
				    MAX-ACCESS  read-only
				    STATUS  current
				    DESCRIPTION
					        "The ac portal number which errcode is 4."
					::= {  dot11AcStats  49 }																				

acMacAuthCuruserNum		    OBJECT-TYPE
				    SYNTAX    Counter32
				    MAX-ACCESS  read-only
				    STATUS  current
				    DESCRIPTION
					        "The Mac Auth user online num."
					::= {  dot11AcStats  50 }					
					
acMacAuthErrLogoffNum		OBJECT-TYPE
				    SYNTAX    Counter32
				    MAX-ACCESS  read-only
				    STATUS  current
				    DESCRIPTION
					        "The Mac Auth user abnormal logoff times."
					::= {  dot11AcStats  51 }
					
acMacAuthReqNum				OBJECT-TYPE
				    SYNTAX    Counter32
				    MAX-ACCESS  read-only
				    STATUS  current
				    DESCRIPTION
					        "The Mac Auth request times."
					::= {  dot11AcStats  52 }
					
acMacAuthReqSuccNum		    OBJECT-TYPE
				    SYNTAX    Counter32
				    MAX-ACCESS  read-only
				    STATUS  current
				    DESCRIPTION
					        "The Mac Auth request success times."
					::= {  dot11AcStats  53 }
					
acMacAuthReqFailNum		    OBJECT-TYPE
				    SYNTAX    Counter32
				    MAX-ACCESS  read-only
				    STATUS  current
				    DESCRIPTION
					        "The Mac Auth request fail times."
					::= {  dot11AcStats  54 }	

acAuthFreeCuruserNum		OBJECT-TYPE
				    SYNTAX    Counter32
				    MAX-ACCESS  read-only
				    STATUS  current
				    DESCRIPTION
					        "The Auth Free user online num."
					::= {  dot11AcStats  55 }					
					
acAuthFreeErrLogoffNum		OBJECT-TYPE
				    SYNTAX    Counter32
				    MAX-ACCESS  read-only
				    STATUS  current
				    DESCRIPTION
					        "The Auth Free user abnormal logoff times."
					::= {  dot11AcStats  56 }
					
acAssocAuthCuruserNum		OBJECT-TYPE
				    SYNTAX    Counter32
				    MAX-ACCESS  read-only
				    STATUS  current
				    DESCRIPTION
					        "The Assoc Auth user online num."
					::= {  dot11AcStats  57 }					
					
acAssocAuthErrLogoffNum		OBJECT-TYPE
				    SYNTAX    Counter32
				    MAX-ACCESS  read-only
				    STATUS  current
				    DESCRIPTION
					        "The Assoc Auth user abnormal logoff times."
					::= {  dot11AcStats  58 }
					
acAssocAuthReqNum				OBJECT-TYPE
				    SYNTAX    Counter32
				    MAX-ACCESS  read-only
				    STATUS  current
				    DESCRIPTION
					        "The Assoc Auth request times."
					::= {  dot11AcStats  59 }
					
acAssocAuthReqSuccNum		    OBJECT-TYPE
				    SYNTAX    Counter32
				    MAX-ACCESS  read-only
				    STATUS  current
				    DESCRIPTION
					        "The Assoc Auth request success times."
					::= {  dot11AcStats  60 }
					
acAssocAuthReqFailNum		    OBJECT-TYPE
				    SYNTAX    Counter32
				    MAX-ACCESS  read-only
				    STATUS  current
				    DESCRIPTION
					        "The Assoc Auth request fail times."
					::= {  dot11AcStats  61 }					
assocAuthOnlineUserNum		    OBJECT-TYPE
				    SYNTAX    INTEGER
				    MAX-ACCESS  read-only
				    STATUS  current
				    DESCRIPTION
					        " The WEP/PSK current user number of AC."
					::= {  dot11AcStats  69}
assocAuthUserLostConnectionCnt		    OBJECT-TYPE
				    SYNTAX    Counter32
				    MAX-ACCESS  read-only
				    STATUS  current
				    DESCRIPTION
					        " The WEP/PSK fail number of AC."
					::= {  dot11AcStats  70 }
assocAuthReqCnt		    OBJECT-TYPE
				    SYNTAX    Counter32
				    MAX-ACCESS  read-only
				    STATUS  current
				    DESCRIPTION
					        " The WEP/PSK request number of AC."
					::= {  dot11AcStats  71 }
assocAuthSucCnt		    OBJECT-TYPE
				    SYNTAX    Counter32
				    MAX-ACCESS  read-only
				    STATUS  current
				    DESCRIPTION
					        " The WEP/PSK request success number of AC."
					::= {  dot11AcStats  72 }
assocAuthReqFailCnt		    OBJECT-TYPE
				    SYNTAX    Counter32
				    MAX-ACCESS  read-only
				    STATUS  current
				    DESCRIPTION
					        " The WEP/PSK request fail number of AC."
					::= {  dot11AcStats  73 }
autoAuthOnlineUserNum		    OBJECT-TYPE
				    SYNTAX    INTEGER
				    MAX-ACCESS  read-only
				    STATUS  current
				    DESCRIPTION
					        " The SIM/PEAP current user number of AC."
					::= {  dot11AcStats  74 }
autoAuthUserLostConnectionCnt		    OBJECT-TYPE
				    SYNTAX    Counter32
				    MAX-ACCESS  read-only
				    STATUS  current
				    DESCRIPTION
					        " The SIM/PEAP fail number of AC."
					::= {  dot11AcStats  75 }
					
					
--********************************************************************************										

acMaxAPNumPermitted		OBJECT-TYPE
				SYNTAX    INTEGER
				MAX-ACCESS  read-only
				STATUS  current
				DESCRIPTION
					"The maximum allowable number of connections of the AP."
				::= {  dot11AcStorageInfo  1 }

acMaxStationNumPermitted	OBJECT-TYPE
				SYNTAX    INTEGER
				MAX-ACCESS  read-only
				STATUS  current
				DESCRIPTION
					"The maximum allowable number of terminals connected."
				::= {  dot11AcStorageInfo  2 }
				
acLoadBalanceStatusBaseOnFlow	OBJECT-TYPE
				SYNTAX    INTEGER{
						    disable(0),
						    enable(1)
						 }
				MAX-ACCESS  read-write
				STATUS  current
				DESCRIPTION
					"AC Load balance status select.(Base on flow)."
				::= {  dot11AcStorageInfo  3 }	
				
acLoadBalanceStatusBaseOnUsr	OBJECT-TYPE
				SYNTAX    INTEGER{
						    disable(0),
						    enable(1)
						 }
				MAX-ACCESS  read-write
				STATUS  current
				DESCRIPTION
					"ACLoad balance status select.(Base on user)."
				::= {  dot11AcStorageInfo  4 }	
				
acLoadBalanceTrigerBaseFlow	OBJECT-TYPE
				SYNTAX    INTEGER(1..30)
				MAX-ACCESS  read-write
				STATUS  current
				DESCRIPTION
					"AC Load balance base on flow."
				::= {  dot11AcStorageInfo  5 }				
				
acLoadBalanceTrigerBaseUsr	OBJECT-TYPE
				SYNTAX    INTEGER(1..10)
				MAX-ACCESS  read-write
				STATUS  current
				DESCRIPTION
					"AC Load balance base on user."
				::= {  dot11AcStorageInfo  6 }							

						

dot11AcInterface 	OBJECT IDENTIFIER ::={ dot11AcGroup 4 }
acIfPortNum     		OBJECT-TYPE
				SYNTAX   INTEGER
				MAX-ACCESS  read-only
				STATUS  current
				DESCRIPTION
					"The total port number of AC. "
				::= { dot11AcInterface  1 }
				
dot11AcIfTable 				OBJECT-TYPE
				    SYNTAX      SEQUENCE OF Dot11AcIfEntry
				    MAX-ACCESS  not-accessible
				    STATUS      current
				    DESCRIPTION
				        "This table shows the AC interface information."
				    ::= { dot11AcInterface 2 }

dot11AcIfEntry  OBJECT-TYPE
    SYNTAX      Dot11AcIfEntry
    MAX-ACCESS  not-accessible
    STATUS      current
    DESCRIPTION
        "AcIf AP information."
    INDEX { ifIndex }
    ::= { dot11AcIfTable 1 }
   
Dot11AcIfEntry ::=SEQUENCE{
		ifIndex		INTEGER,
		ifDescr		DisplayString,
		ifType		INTEGER,
		ifMTU		INTEGER,
		ifSpeed		Gauge32,
		ifPhysAddress	PhysAddress,
		ifAdminStatus	INTEGER,
		ifOperStatus	INTEGER,
		ifLastChange	TimeTicks,
		ifUpDwnTimes	INTEGER
}
ifIndex		OBJECT-TYPE
		SYNTAX    INTEGER
		MAX-ACCESS  read-only
		STATUS  current
		DESCRIPTION
			"Interface index."
		::= {  dot11AcIfEntry  1 }

ifDescr		OBJECT-TYPE
		SYNTAX    DisplayString
		MAX-ACCESS  read-only
		STATUS  current
		DESCRIPTION
			"Interface description."
		::= {  dot11AcIfEntry  2 }

ifType		OBJECT-TYPE
		SYNTAX    INTEGER{
				other(1),          -- none of the following
                          regular1822(2),
                          hdh1822(3),
                          ddn-x25(4),
                          rfc877-x25(5),
                          ethernet-csmacd(6),
                          iso88023-csmacd(7),
                          iso88024-tokenBus(8),
                          iso88025-tokenRing(9),
                          iso88026-man(10),
                          starLan(11),
                          proteon-10Mbit(12),
                          proteon-80Mbit(13),
                          hyperchannel(14),
                          fddi(15),
                          lapb(16),
                          sdlc(17),
                          ds1(18),           -- T-1
                          e1(19),            -- european equiv. of T-1
                          basicISDN(20),
                          primaryISDN(21),   -- proprietary serial
                          propPointToPointSerial(22),
                          ppp(23),
                          softwareLoopback(24),
                          eon(25),            -- CLNP over IP [11]
                          ethernet-3Mbit(26),
                          nsip(27),           -- XNS over IP
                          slip(28),           -- generic SLIP
                          ultra(29),          -- ULTRA technologies
                          ds3(30),            -- T-3
                          sip(31),            -- SMDS
                          frame-relay(32)

				}
		MAX-ACCESS  read-only
		STATUS  current
		DESCRIPTION
			"Interface type."
		::= {  dot11AcIfEntry  3 }

ifMTU		OBJECT-TYPE
		SYNTAX    INTEGER
		MAX-ACCESS  read-only
		STATUS  current
		DESCRIPTION
			"Interface MTU."
		::= {  dot11AcIfEntry  4 }

ifSpeed		OBJECT-TYPE
		SYNTAX    Gauge32
		MAX-ACCESS  read-only
		STATUS  current
		DESCRIPTION
			"Interface speed."
		::= {  dot11AcIfEntry  5 }

ifPhysAddress	OBJECT-TYPE
		SYNTAX    PhysAddress
		MAX-ACCESS  read-only
		STATUS  current
		DESCRIPTION
			"Interface physic address."
		::= {  dot11AcIfEntry  6 }

ifAdminStatus	OBJECT-TYPE
		SYNTAX    INTEGER{
				up(1),
				down(2)	
				}
		MAX-ACCESS  read-write
		STATUS  current
		DESCRIPTION
			"Interface physic admin status."
		::= {  dot11AcIfEntry  7 }

ifOperStatus	OBJECT-TYPE
		SYNTAX    INTEGER{
				up(1),
				down(2),
				adminDown(3)
				}
		MAX-ACCESS  read-only
		STATUS  current
		DESCRIPTION
			"Interface physic current status."
		::= {  dot11AcIfEntry  8 }

ifLastChange	OBJECT-TYPE
		SYNTAX    TimeTicks
		MAX-ACCESS  read-only
		STATUS  current
		DESCRIPTION
			"The last time that device into currentwork mode."
		::= {  dot11AcIfEntry  9 }
		
ifUpDwnTimes	OBJECT-TYPE
		SYNTAX    INTEGER
		MAX-ACCESS  read-only
		STATUS  current
		DESCRIPTION
			"The interface up-down times."
		::= {  dot11AcIfEntry  10 }
		
dot11AcIfCapabilityTable 		OBJECT-TYPE
					SYNTAX      SEQUENCE OF Dot11AcIfCapabilityEntry
					MAX-ACCESS  not-accessible
					STATUS      current
					DESCRIPTION
					"This table shows the AC interface capability information."
					::= { dot11AcInterface 3 }

dot11AcIfCapabilityEntry  	OBJECT-TYPE
				SYNTAX      Dot11AcIfCapabilityEntry
				MAX-ACCESS  not-accessible
				STATUS      current
				DESCRIPTION
				"AC interface capability information."
				INDEX { ifIndex }
				::= { dot11AcIfCapabilityTable 1 }
   
Dot11AcIfCapabilityEntry ::=SEQUENCE{
		acIfInUcastPkts			Counter64,
		acIfInNUcastPkts		Counter64,
		acIfInOctets			Counter64,
		acIfInDiscardPkts		Counter32,
		acIfInErrors			Counter32,
		acIfOutUcastPkts		Counter64,
		acIfOutNUcastPkts		Counter64,
		acIfOutOctets			Counter64,
		acIfOutDiscardPkts		Counter32,
		acIfOutErrors			Counter32,
		acIfUpDwnTimes			Counter32,
		acIfInMulticastPkts		Counter32,
		acIfOutMulticastPkts		Counter32,
		acUplinkRate     		Counter64,
		acDownlinkRate			Counter64,
		acBandwidthUsage		Counter32,
		acDropUsage			Counter32,
		acIfOutBroadcastPkts		Counter32,
		acUplinkKbyteRate		Counter32,
		acDownlinkKbyteRate		Counter32,
		acipv6IfInReceivesPkts		Counter64,
		acipv6IfInHdrErrorsPkts		Counter64,
		acipv6IfInTooBigErrorsPkts	Counter64,
		acipv6IfInNoRoutesPkts			Counter64,
		acipv6IfInAddrErrorsPkts		Counter64,
		acipv6IfInUnknownProtosPkts		Counter64,
		acipv6IfInTruncatedPkts		Counter64,
		acipv6IfInDiscardsPkts		Counter64,
		acipv6IfInDeliversPkts		Counter64,
		acipv6IfOutForwDatagramsPkts		Counter64,
		acipv6IfOutRequestsPkts			Counter64,
		acipv6IfOutDiscardsPkts			Counter64,
		acipv6IfOutFragOKsPkts		Counter64,
		acipv6IfOutFragFailsPkts 		Counter64,
		acipv6IfOutFragCreatesPkts		Counter64,
		acipv6IfReasmReqdsPkts			Counter64,
		acipv6IfReasmOKsPkts			Counter64,
		acipv6IfReasmFailsPkts			Counter64,
		acipv6IfInMcastPkts   Counter64,
		acipv6IfOutMcastPkts	Counter64	
}
acIfInUcastPkts			OBJECT-TYPE
				SYNTAX    Counter64
				MAX-ACCESS  read-only
				STATUS  current
				DESCRIPTION
					"The total number of unicast packets the interface received."
				::= {  dot11AcIfCapabilityEntry  1 }

acIfInNUcastPkts		OBJECT-TYPE
				SYNTAX    Counter64
				MAX-ACCESS  read-only
				STATUS  current
				DESCRIPTION
					"The total number of non-unicast packets the interface received."
				::= {  dot11AcIfCapabilityEntry  2 }

acIfInOctets			OBJECT-TYPE
				SYNTAX    Counter64
				MAX-ACCESS  read-only
				STATUS  current
				DESCRIPTION
					"The total number of bytes the interface received."
				::= {  dot11AcIfCapabilityEntry  3 }

acIfInDiscardPkts		OBJECT-TYPE
				SYNTAX    Counter32
				MAX-ACCESS  read-only
				STATUS  current
				DESCRIPTION
					"The total number of  packets the interface received and discarded."
				::= {  dot11AcIfCapabilityEntry  4 }

acIfInErrors			OBJECT-TYPE
				SYNTAX    Counter32
				MAX-ACCESS  read-only
				STATUS  current
				DESCRIPTION
					"The total number of error packets the interface received."
				::= {  dot11AcIfCapabilityEntry  5 }

acIfOutUcastPkts		OBJECT-TYPE
				SYNTAX    Counter64
				MAX-ACCESS  read-only
				STATUS  current
				DESCRIPTION
					"The total number of unicast packets the interface transmited."
				::= {  dot11AcIfCapabilityEntry  6 }

acIfOutNUcastPkts		OBJECT-TYPE
				SYNTAX    Counter64
				MAX-ACCESS  read-only
				STATUS  current
				DESCRIPTION
					"The total number of non-unicast packets the interface transmited."
				::= {  dot11AcIfCapabilityEntry  7 }

acIfOutOctets			OBJECT-TYPE
				SYNTAX    Counter64
				MAX-ACCESS  read-only
				STATUS  current
				DESCRIPTION
					"The total number of bytes the interface transmited."
				::= {  dot11AcIfCapabilityEntry  8 }

acIfOutDiscardPkts		OBJECT-TYPE
				SYNTAX    Counter32
				MAX-ACCESS  read-only
				STATUS  current
				DESCRIPTION
					"The total number of  packets the interface transmited and discarded."
				::= {  dot11AcIfCapabilityEntry  9 }

acIfOutErrors			OBJECT-TYPE
				SYNTAX    Counter32
				MAX-ACCESS  read-only
				STATUS  current
				DESCRIPTION
					"The total number of error packets the interface transmited."
				::= {  dot11AcIfCapabilityEntry  10 }

acIfUpDwnTimes			OBJECT-TYPE
				SYNTAX    Counter32
				MAX-ACCESS  read-only
				STATUS  current
				DESCRIPTION
					"The interface up-down times."
				::= {  dot11AcIfCapabilityEntry  11 }

acIfInMulticastPkts		OBJECT-TYPE
				SYNTAX    Counter32
				MAX-ACCESS  read-only
				STATUS  current
				DESCRIPTION
					"Multicast packets received."
				::= {  dot11AcIfCapabilityEntry  12 }

acIfOutMulticastPkts		OBJECT-TYPE
				SYNTAX    Counter32
				MAX-ACCESS  read-only
				STATUS  current
				DESCRIPTION
					"Multicast packets sent."
				::= {  dot11AcIfCapabilityEntry  13 }
				
acUplinkRate			OBJECT-TYPE
				SYNTAX    Counter64
				MAX-ACCESS  read-only
				STATUS  current
				DESCRIPTION
					"The  ac uplink rate."
				::= {  dot11AcIfCapabilityEntry  14 }
				
acDownlinkRate			OBJECT-TYPE
				SYNTAX    Counter64
				MAX-ACCESS  read-only
				STATUS  current
				DESCRIPTION
					"The  ac downlink rate."
				::= {  dot11AcIfCapabilityEntry  15 }	

acBandwidthUsage		OBJECT-TYPE
				SYNTAX    Counter32
				MAX-ACCESS  read-only
				STATUS  current
				DESCRIPTION
					"The  ac Bandwidth usage."
				::= {  dot11AcIfCapabilityEntry  16 }	
				
acDropUsage			OBJECT-TYPE
				SYNTAX    Counter32
				MAX-ACCESS  read-only
				STATUS  current
				DESCRIPTION
					"The  ac drop pkts usage."
				::= {  dot11AcIfCapabilityEntry  17 }

acIfOutBroadcastPkts		OBJECT-TYPE
				SYNTAX    Counter32
				MAX-ACCESS  read-only
				STATUS  current
				DESCRIPTION
					"Broadcast pkts send."
				::= {  dot11AcIfCapabilityEntry  18 }

acUplinkKbyteRate		OBJECT-TYPE
				SYNTAX    Counter32
				MAX-ACCESS  read-only
				STATUS  current
				DESCRIPTION
					"The  ac uplink rate.(unit(Kbyte/s))"
				::= {  dot11AcIfCapabilityEntry  19 }
				
acDownlinkKbyteRate		OBJECT-TYPE
				SYNTAX    Counter32
				MAX-ACCESS  read-only
				STATUS  current
				DESCRIPTION
					"The  ac downlink rate.(unit(Kbyte/s))"
				::= {  dot11AcIfCapabilityEntry  20 }					

acipv6IfInReceivesPkts			OBJECT-TYPE
				SYNTAX    Counter64
				MAX-ACCESS  read-only
				STATUS  current
				DESCRIPTION
					"The total number of ipv6 packets the interface received."
				::= {  dot11AcIfCapabilityEntry  21 }
				
acipv6IfInHdrErrorsPkts			OBJECT-TYPE
				SYNTAX    Counter64
				MAX-ACCESS  read-only
				STATUS  current
				DESCRIPTION
					"The total number of ipv6 packets the interface ready to throw away."
				::= {  dot11AcIfCapabilityEntry  22 }
				
acipv6IfInTooBigErrorsPkts			OBJECT-TYPE
				SYNTAX    Counter64
				MAX-ACCESS  read-only
				STATUS  current
				DESCRIPTION
					"The total number of ipv6 packets those of too big to forward."
				::= {  dot11AcIfCapabilityEntry  23 }
				
acipv6IfInNoRoutesPkts			OBJECT-TYPE
				SYNTAX    Counter64
				MAX-ACCESS  read-only
				STATUS  current
				DESCRIPTION
					"The total number of ipv6 packets those of no routing and discarded."
				::= {  dot11AcIfCapabilityEntry  24 }
				
acipv6IfInAddrErrorsPkts			OBJECT-TYPE
				SYNTAX    Counter64
				MAX-ACCESS  read-only
				STATUS  current
				DESCRIPTION
					"The total number of ipv6 packets due to the input of IPv6 address illegal ."
				::= {  dot11AcIfCapabilityEntry  25 }
				
acipv6IfInUnknownProtosPkts			OBJECT-TYPE
				SYNTAX    Counter64
				MAX-ACCESS  read-only
				STATUS  current
				DESCRIPTION
					"The total number of ipv6 packets due to unknown or does not support agreement ."
				::= {  dot11AcIfCapabilityEntry  26 }
				
acipv6IfInTruncatedPkts			OBJECT-TYPE
				SYNTAX    Counter64
				MAX-ACCESS  read-only
				STATUS  current
				DESCRIPTION
					"The total number of ipv6 packets due to the incomplete data ."
				::= {  dot11AcIfCapabilityEntry  27 }
				
acipv6IfInDiscardsPkts			OBJECT-TYPE
				SYNTAX    Counter64
				MAX-ACCESS  read-only
				STATUS  current
				DESCRIPTION
					"The total number of ipv6 packets unable to continue processing ."
				::= {  dot11AcIfCapabilityEntry  28 }
				
acipv6IfInDeliversPkts			OBJECT-TYPE
				SYNTAX    Counter64
				MAX-ACCESS  read-only
				STATUS  current
				DESCRIPTION
					"The total number of ipv6 packets all ipv6 user agreement sent successfully ."
				::= {  dot11AcIfCapabilityEntry  29 }
				
acipv6IfOutForwDatagramsPkts			OBJECT-TYPE
				SYNTAX    Counter64
				MAX-ACCESS  read-only
				STATUS  current
				DESCRIPTION
					"The total number of ipv6 packets those received and forwarded to the final node successfully ."
				::= {  dot11AcIfCapabilityEntry  30 }
				
acipv6IfOutRequestsPkts			OBJECT-TYPE
				SYNTAX    Counter64
				MAX-ACCESS  read-only
				STATUS  current
				DESCRIPTION
					"Transport requirements of the local IPv6 all user agreement output message number ."
				::= {  dot11AcIfCapabilityEntry  31 }
				
acipv6IfOutDiscardsPkts			OBJECT-TYPE
				SYNTAX    Counter64
				MAX-ACCESS  read-only
				STATUS  current
				DESCRIPTION
					"Due to be continue to transmit discarded IPv6 output message number ."
				::= {  dot11AcIfCapabilityEntry  32 }
				
acipv6IfOutFragOKsPkts			OBJECT-TYPE
				SYNTAX    Counter64
				MAX-ACCESS  read-only
				STATUS  current
				DESCRIPTION
					"Output interface successful shard of IPv6 output message number ."
				::= {  dot11AcIfCapabilityEntry  33 }
				
acipv6IfOutFragFailsPkts			OBJECT-TYPE
				SYNTAX    Counter64
				MAX-ACCESS  read-only
				STATUS  current
				DESCRIPTION
					"Due to the output interface to fragmentation and number of IPv6 packet is discarded ."
				::= {  dot11AcIfCapabilityEntry  34 }
				
acipv6IfOutFragCreatesPkts			OBJECT-TYPE
				SYNTAX    Counter64
				MAX-ACCESS  read-only
				STATUS  current
				DESCRIPTION
					"Output interface based on fragmentation results of IPv6 packet fragmentation ."
				::= {  dot11AcIfCapabilityEntry  35 }
				
acipv6IfReasmReqdsPkts			OBJECT-TYPE
				SYNTAX    Counter64
				MAX-ACCESS  read-only
				STATUS  current
				DESCRIPTION
					"IPv6 subdivision number of interfaces need to restructure ."
				::= {  dot11AcIfCapabilityEntry  36 }
				
acipv6IfReasmOKsPkts			OBJECT-TYPE
				SYNTAX    Counter64
				MAX-ACCESS  read-only
				STATUS  current
				DESCRIPTION
					"Successful restructuring of IPv6 packet number ."
				::= {  dot11AcIfCapabilityEntry  37 }
				
acipv6IfReasmFailsPkts			OBJECT-TYPE
				SYNTAX    Counter64
				MAX-ACCESS  read-only
				STATUS  current
				DESCRIPTION
					"Due to the failure of fragmentation of IPv6 reorganization algorithm ."
				::= {  dot11AcIfCapabilityEntry  38 }
				
acipv6IfInMcastPkts			OBJECT-TYPE
				SYNTAX    Counter64
				MAX-ACCESS  read-only
				STATUS  current
				DESCRIPTION
					"Interface receives the IPv6 multicast packets ."
				::= {  dot11AcIfCapabilityEntry  39 }
				
acipv6IfOutMcastPkts			OBJECT-TYPE
				SYNTAX    Counter64
				MAX-ACCESS  read-only
				STATUS  current
				DESCRIPTION
					"Interface transmit IPv6 multicast packets ."
				::= {  dot11AcIfCapabilityEntry  40 }
				

dot11AcInterfaceTable OBJECT-TYPE
			    SYNTAX      SEQUENCE OF Dot11AcInterfaceEntry
			    MAX-ACCESS  not-accessible
			    STATUS      current
			    DESCRIPTION
			        "This table show the interface information of AC."
			    ::= { dot11AcInterface 4 }

dot11AcInterfaceEntry  OBJECT-TYPE
			    SYNTAX      Dot11AcInterfaceEntry
			    MAX-ACCESS  not-accessible
			    STATUS      current
			    DESCRIPTION
			        "Show interface information of AC."
			    INDEX { ifIndex }
			    ::= { dot11AcInterfaceTable 1 }

Dot11AcInterfaceEntry ::=SEQUENCE{
					AcInterfaceName		DisplayString,
					AcInterfaceIP		IpAddress,
					AcInterfaceNetMask	IpAddress,
					AcInterfaceIPV6		InetAddressIPv6,
					AcInterfaceIPV6prefix	INTEGER
				}

AcInterfaceName	 			OBJECT-TYPE
					SYNTAX     	DisplayString
					MAX-ACCESS 	read-only
					STATUS     	current
					DESCRIPTION
				        	"AC Interface Name."
					::= { dot11AcInterfaceEntry 1 }

AcInterfaceIP 				OBJECT-TYPE
					SYNTAX      	IpAddress
					MAX-ACCESS  	read-write
					STATUS      	current
					DESCRIPTION
					      "AC Interface IP."
					::= { dot11AcInterfaceEntry 2 }
					
AcInterfaceNetMask 			OBJECT-TYPE
					SYNTAX      	IpAddress
					MAX-ACCESS  	read-write
					STATUS      	current
					DESCRIPTION
					      "AC Interface NetMask."
					::= { dot11AcInterfaceEntry 3 }

AcInterfaceIPV6 				OBJECT-TYPE
					SYNTAX      	InetAddressIPv6
					MAX-ACCESS  	read-write
					STATUS      	current
					DESCRIPTION
					      "AC Interface IPV6 address."
					::= { dot11AcInterfaceEntry 4 }
					
AcInterfaceIPV6prefix 			OBJECT-TYPE
					SYNTAX      	INTEGER
					MAX-ACCESS  	read-write
					STATUS      	current
					DESCRIPTION
					      "AC Interface IPV6 Prefix."
					::= { dot11AcInterfaceEntry 5 }


acPhyPortNum     	OBJECT-TYPE
			SYNTAX   INTEGER
			MAX-ACCESS  read-only
			STATUS  current
			DESCRIPTION
				"The total physical port number of AC. "
			::= { dot11AcInterface  5 }
			
dot11AcPhyPortTable	    OBJECT-TYPE
			    SYNTAX      SEQUENCE OF Dot11AcPhyPortEntry
			    MAX-ACCESS  not-accessible
			    STATUS      current
			    DESCRIPTION
			        "This table shows the AC physical port information."
			    ::= { dot11AcInterface 6 }

dot11AcPhyPortEntry  OBJECT-TYPE
	    SYNTAX      Dot11AcPhyPortEntry
	    MAX-ACCESS  not-accessible
	    STATUS      current
	    DESCRIPTION
	        "Ac Physical Port information."
	    INDEX { PhyPortIndex }
	    ::= { dot11AcPhyPortTable 1 }
   
Dot11AcPhyPortEntry ::=SEQUENCE{
			PhyPortIndex		INTEGER,
			PhyPortDescr		DisplayString,
			PhyPortType		INTEGER,
			PhyPortMTU		INTEGER,
			PhyPortSpeed		Gauge32,
			PhyPortPhysAddress	PhysAddress,
			PhyPortAdminStatus	INTEGER,
			PhyPortOperStatus	INTEGER,
			PhyPortLastChange	TimeTicks,
			PhyPortUpDwnTimes	INTEGER
}
PhyPortIndex		OBJECT-TYPE
			SYNTAX    INTEGER
			MAX-ACCESS  read-only
			STATUS  current
			DESCRIPTION
				"Physical port index."
			::= {  dot11AcPhyPortEntry  1 }

PhyPortDescr		OBJECT-TYPE
			SYNTAX    DisplayString
			MAX-ACCESS  read-only
			STATUS  current
			DESCRIPTION
				"Physical port description."
			::= {  dot11AcPhyPortEntry  2 }

PhyPortType		OBJECT-TYPE
			SYNTAX    INTEGER{
					ETH-INVALID(1),
					ETH-FE-TX(2),
					ETH-FE-FIBER(3),
					ETH-GTX(4),
					ETH-GE-FIBER(5),
					ETH-GE-SFP(6),
					ETH-XGE-XFP(7),
					ETH-XGTX(8),
					ETH-XGE-FIBER(9)
					}
			MAX-ACCESS  read-only
			STATUS  current
			DESCRIPTION
				"Physical port type."
			::= {  dot11AcPhyPortEntry  3 }

PhyPortMTU		OBJECT-TYPE
			SYNTAX    INTEGER
			MAX-ACCESS  read-only
			STATUS  current
			DESCRIPTION
				"Physical port MTU."
			::= {  dot11AcPhyPortEntry  4 }

PhyPortSpeed		OBJECT-TYPE
			SYNTAX    Gauge32
			MAX-ACCESS  read-only
			STATUS  current
			DESCRIPTION
				"Physical port speed."
			::= {  dot11AcPhyPortEntry  5 }

PhyPortPhysAddress	OBJECT-TYPE
			SYNTAX    PhysAddress
			MAX-ACCESS  read-only
			STATUS  current
			DESCRIPTION
				"Physical port physic address."
			::= {  dot11AcPhyPortEntry  6 }

PhyPortAdminStatus	OBJECT-TYPE
			SYNTAX    INTEGER{
					up(1),
					down(2)	
					}
			MAX-ACCESS  read-write
			STATUS  current
			DESCRIPTION
				"Physical port admin status."
			::= {  dot11AcPhyPortEntry  7 }

PhyPortOperStatus	OBJECT-TYPE
			SYNTAX    INTEGER{
					up(1),
					down(2),
					adminDown(3)
					}
			MAX-ACCESS  read-only
			STATUS  current
			DESCRIPTION
				"Physical port current status."
			::= {  dot11AcPhyPortEntry  8 }

PhyPortLastChange	OBJECT-TYPE
			SYNTAX    TimeTicks
			MAX-ACCESS  read-only
			STATUS  current
			DESCRIPTION
				"The last time that physical port into current state."
			::= {  dot11AcPhyPortEntry  9 }
			
PhyPortUpDwnTimes	OBJECT-TYPE
			SYNTAX    INTEGER
			MAX-ACCESS  read-only
			STATUS  current
			DESCRIPTION
				"The Physical port up-down times."
			::= {  dot11AcPhyPortEntry  10 }
			
dot11AcPhyPortCapabilityTable 		OBJECT-TYPE
					SYNTAX      SEQUENCE OF Dot11AcPhyPortCapabilityEntry
					MAX-ACCESS  not-accessible
					STATUS      current
					DESCRIPTION
					"This table shows the AC physical port capability information."
					::= { dot11AcInterface 7 }

dot11AcPhyPortCapabilityEntry  	OBJECT-TYPE
				SYNTAX      Dot11AcPhyPortCapabilityEntry
				MAX-ACCESS  not-accessible
				STATUS      current
				DESCRIPTION
				"AC Physical port capability information."
				INDEX { PhyPortIndex }
				::= { dot11AcPhyPortCapabilityTable 1 }
   
Dot11AcPhyPortCapabilityEntry ::=SEQUENCE{
		acPhyPortInUcastPkts		Counter64,
		acPhyPortInNUcastPkts		Counter64,
		acPhyPortInOctets		Counter64,
		acPhyPortInDiscardPkts		Counter32,
		acPhyPortInErrors		Counter32,
		acPhyPortOutUcastPkts		Counter64,
		acPhyPortOutNUcastPkts		Counter64,
		acPhyPortOutOctets		Counter64,
		acPhyPortOutDiscardPkts		Counter32,
		acPhyPortOutErrors		Counter32,
		acPhyPortInMulticastPkts	Counter32,
		acPhyPortOutMulticastPkts	Counter32
}
acPhyPortInUcastPkts		OBJECT-TYPE
				SYNTAX    Counter64
				MAX-ACCESS  read-only
				STATUS  current
				DESCRIPTION
					"The total number of unicast packets the physical port received."
				::= {  dot11AcPhyPortCapabilityEntry  1 }

acPhyPortInNUcastPkts		OBJECT-TYPE
				SYNTAX    Counter64
				MAX-ACCESS  read-only
				STATUS  current
				DESCRIPTION
					"The total number of non-unicast packets the physical port received."
				::= {  dot11AcPhyPortCapabilityEntry  2 }

acPhyPortInOctets		OBJECT-TYPE
				SYNTAX    Counter64
				MAX-ACCESS  read-only
				STATUS  current
				DESCRIPTION
					"The total number of bytes the physical port received."
				::= {  dot11AcPhyPortCapabilityEntry  3 }

acPhyPortInDiscardPkts		OBJECT-TYPE
				SYNTAX    Counter32
				MAX-ACCESS  read-only
				STATUS  current
				DESCRIPTION
					"The total number of packets the physical port received and discarded."
				::= {  dot11AcPhyPortCapabilityEntry  4 }

acPhyPortInErrors		OBJECT-TYPE
				SYNTAX    Counter32
				MAX-ACCESS  read-only
				STATUS  current
				DESCRIPTION
					"The total number of error packets the physical port received."
				::= {  dot11AcPhyPortCapabilityEntry  5 }

acPhyPortOutUcastPkts		OBJECT-TYPE
				SYNTAX    Counter64
				MAX-ACCESS  read-only
				STATUS  current
				DESCRIPTION
					"The total number of unicast packets the physical port sent."
				::= {  dot11AcPhyPortCapabilityEntry  6 }

acPhyPortOutNUcastPkts		OBJECT-TYPE
				SYNTAX    Counter64
				MAX-ACCESS  read-only
				STATUS  current
				DESCRIPTION
					"The total number of non-unicast packets the physical port sent."
				::= {  dot11AcPhyPortCapabilityEntry  7 }

acPhyPortOutOctets		OBJECT-TYPE
				SYNTAX    Counter64
				MAX-ACCESS  read-only
				STATUS  current
				DESCRIPTION
					"The total number of bytes the physical port sent."
				::= {  dot11AcPhyPortCapabilityEntry  8 }

acPhyPortOutDiscardPkts		OBJECT-TYPE
				SYNTAX    Counter32
				MAX-ACCESS  read-only
				STATUS  current
				DESCRIPTION
					"The total number of packets the physical port sent and discarded."
				::= {  dot11AcPhyPortCapabilityEntry  9 }

acPhyPortOutErrors		OBJECT-TYPE
				SYNTAX    Counter32
				MAX-ACCESS  read-only
				STATUS  current
				DESCRIPTION
					"The total number of error packets the physical port sent."
				::= {  dot11AcPhyPortCapabilityEntry  10 }

acPhyPortInMulticastPkts	OBJECT-TYPE
				SYNTAX    Counter32
				MAX-ACCESS  read-only
				STATUS  current
				DESCRIPTION
					"The total number of multicast packets the physical port received."
				::= {  dot11AcPhyPortCapabilityEntry  11 }

acPhyPortOutMulticastPkts		OBJECT-TYPE
				SYNTAX    Counter32
				MAX-ACCESS  read-only
				STATUS  current
				DESCRIPTION
					"The total number of multicast packets the physical port sent."
				::= {  dot11AcPhyPortCapabilityEntry  12 }
				

dot11Rogue	OBJECT IDENTIFIER ::={ dot11AcGroup 5 }

dot11RogueTable 	OBJECT-TYPE
		    	SYNTAX      SEQUENCE OF Dot11RogueEntry
		    	MAX-ACCESS  not-accessible
		    	STATUS      current
		    	DESCRIPTION
		        	"This table shows the Rogue AP information."
		    	::= { dot11Rogue 1 }

dot11RogueEntry  	OBJECT-TYPE
    			SYNTAX      Dot11RogueEntry
    			MAX-ACCESS  not-accessible
    			STATUS      current
    			DESCRIPTION
        			"Rogue AP information."
    			INDEX { RogueAPIndex }
    			::= { dot11RogueTable 1 }
   
Dot11RogueEntry ::=SEQUENCE{
	RogueAPIndex				INTEGER,
	RogueAPMac				DisplayString,
	RogueAPRssi				INTEGER,
	RogueAPMonitorNum			INTEGER,
	RogueAPRxSignalIntensity		INTEGER,
	RogueAPFirstDetectTm			DisplayString,
	RogueAPLastDetectTm			DisplayString,
	RogueAPSSID				DisplayString,
	RogueAPMaxSigStrength			INTEGER,
	RogueAPChannel				INTEGER,
	RogueAPEncryptAgrithm			INTEGER,
	RogueAPAttackedStatus			TruthValue,
	RogueAPToIgnore				TruthValue,
	RogueAPManufacturer			DisplayString
	}
RogueAPIndex				OBJECT-TYPE
					SYNTAX      	INTEGER
					MAX-ACCESS  	read-only
					STATUS      	current
					DESCRIPTION
					      "The rogue AP Index."
					::= { dot11RogueEntry 1 }

RogueAPMac 				OBJECT-TYPE
					SYNTAX      	DisplayString
					MAX-ACCESS  	read-only
					STATUS      	current
					DESCRIPTION
					      "The rogue AP MAC address."
					::= { dot11RogueEntry 2 }

RogueAPRssi	 			OBJECT-TYPE
					SYNTAX     	INTEGER 
					MAX-ACCESS 	read-only
					STATUS     	current
					DESCRIPTION
				        	"The rogue AP RSSI."
					::= { dot11RogueEntry 3 }

RogueAPMonitorNum 			OBJECT-TYPE
					SYNTAX      	INTEGER
					MAX-ACCESS  	read-only
					STATUS      	current
					DESCRIPTION
				      		"The monitor AP number which detect rogue AP."
					::= { dot11RogueEntry 4 }

RogueAPRxSignalIntensity		OBJECT-TYPE
					SYNTAX     	INTEGER 
					MAX-ACCESS 	read-only
					STATUS     	current
					DESCRIPTION
				        	"The rogue AP receive signal intensity."
					::= { dot11RogueEntry 5 }

RogueAPFirstDetectTm			OBJECT-TYPE
					SYNTAX      	DisplayString
					MAX-ACCESS  	read-only
					STATUS      	current
					DESCRIPTION
					      "The first time that detect the rogue AP."
					::= { dot11RogueEntry 6 }

RogueAPLastDetectTm			OBJECT-TYPE
					SYNTAX      	DisplayString
					MAX-ACCESS  	read-only
					STATUS      	current
					DESCRIPTION
					      "The last time that detect the rogue AP."
					::= { dot11RogueEntry 7 }

RogueAPSSID				OBJECT-TYPE
					SYNTAX      	DisplayString
					MAX-ACCESS  	read-only
					STATUS      	current
					DESCRIPTION
					      "Rogue AP SSID."
					::= { dot11RogueEntry 8 }

RogueAPMaxSigStrength			OBJECT-TYPE
					SYNTAX      	INTEGER
					MAX-ACCESS  	read-only
					STATUS      	current
					DESCRIPTION
					      "WIDS receive from the suspect the maximum AP signal strength."
					::= { dot11RogueEntry 9 }

RogueAPChannel				OBJECT-TYPE
					SYNTAX      	INTEGER
					MAX-ACCESS  	read-only
					STATUS      	current
					DESCRIPTION
					      "Rogue AP channel."
					::= { dot11RogueEntry 10 }


RogueAPEncryptAgrithm			OBJECT-TYPE
					SYNTAX      	INTEGER{
								noEncry(0),
								wep(1),
								wpa1(2),
								wpa2(3)
								}
					MAX-ACCESS  	read-only
					STATUS      	current
					DESCRIPTION
					      "Encryption method of the rogue AP frame."
					::= { dot11RogueEntry 11 }


RogueAPAttackedStatus			OBJECT-TYPE
					SYNTAX      	TruthValue
					MAX-ACCESS  	read-write
					STATUS      	current
					DESCRIPTION
					      "Whether strategies to the rogue AP."
					::= { dot11RogueEntry 12 }

RogueAPToIgnore				OBJECT-TYPE
					SYNTAX      	TruthValue
					MAX-ACCESS  	read-write
					STATUS      	current
					DESCRIPTION
					      "Whether or not ignore the rogue AP."
					::= { dot11RogueEntry 13 }
					
RogueAPManufacturer			OBJECT-TYPE
					SYNTAX      	DisplayString
					MAX-ACCESS  	read-only
					STATUS      	current
					DESCRIPTION
					      "Rogue AP manufacturer."
					::= { dot11RogueEntry 14 }
					
dot11RogueStaTable 	OBJECT-TYPE
		    	SYNTAX      SEQUENCE OF Dot11RogueStaEntry
		    	MAX-ACCESS  not-accessible
		    	STATUS      current
		    	DESCRIPTION
		        	"This table shows the Rogue station information."
		    	::= { dot11Rogue 2 }

dot11RogueStaEntry  	OBJECT-TYPE
    			SYNTAX      Dot11RogueStaEntry
    			MAX-ACCESS  not-accessible
    			STATUS      current
    			DESCRIPTION
        			"Rogue AP information."
    			INDEX { rogueStaIndex }
    			::= { dot11RogueStaTable 1 }
Dot11RogueStaEntry ::=SEQUENCE{
		rogueStaIndex			INTEGER,
		rogueStaMac			DisplayString,
		rogueStaMonitorNum		INTEGER,
		rogueStaFirstDetectTm		DisplayString,
		rogueStaLastDetectTm	        DisplayString,
		rogueStaAccessBSSID		DisplayString,
		rogueStaMaxSigStrength		INTEGER,
		rogueStaChannel			INTEGER,
		rogueStaAdHocStatus		TruthValue,
		rogueStaAttackStatus		TruthValue,
		rogueStaToIgnore		TruthValue,
		rogueStaManufacturer		DisplayString
}
rogueStaIndex			OBJECT-TYPE
				SYNTAX      	INTEGER
				MAX-ACCESS  	read-only
				STATUS      	current
				DESCRIPTION
				      "Rogue station index."
				::= { dot11RogueStaEntry 1 }

rogueStaMac			OBJECT-TYPE
				SYNTAX      	DisplayString
				MAX-ACCESS  	read-only
				STATUS      	current
				DESCRIPTION
				      "Rogue station mac."
				::= { dot11RogueStaEntry 2 }

rogueStaMonitorNum		OBJECT-TYPE
				SYNTAX      	INTEGER
				MAX-ACCESS  	read-only
				STATUS      	current
				DESCRIPTION
				      "The station number that detect rogue station."
				::= { dot11RogueStaEntry 3 }

rogueStaFirstDetectTm		OBJECT-TYPE
				SYNTAX          DisplayString
				MAX-ACCESS  	read-only
				STATUS      	current
				DESCRIPTION
				      "The first time that detect rogue station."
				::= { dot11RogueStaEntry 4 }


rogueStaLastDetectTm		OBJECT-TYPE
				SYNTAX      	DisplayString
				MAX-ACCESS  	read-only
				STATUS      	current
				DESCRIPTION
				      "The last time that detect rogue station."
				::= { dot11RogueStaEntry 5 }

rogueStaAccessBSSID		OBJECT-TYPE
				SYNTAX      	DisplayString
				MAX-ACCESS  	read-only
				STATUS      	current
				DESCRIPTION
				      "The rogue station access BSSID."
				::= { dot11RogueStaEntry 6 }

rogueStaMaxSigStrength		OBJECT-TYPE
				SYNTAX      	INTEGER
				MAX-ACCESS  	read-only
				STATUS      	current
				DESCRIPTION
				      "WIDS receive from the suspect the maximum station signal strength."
				::= { dot11RogueStaEntry 7 }

rogueStaChannel			OBJECT-TYPE
				SYNTAX      	INTEGER
				MAX-ACCESS  	read-only
				STATUS      	current
				DESCRIPTION
				      "Rogue station number."
				::= { dot11RogueStaEntry 8 }

rogueStaAdHocStatus		OBJECT-TYPE
				SYNTAX      	TruthValue
				MAX-ACCESS  	read-only
				STATUS      	current
				DESCRIPTION
				      "Rogue station whether works in Ad-Hoc mode."
				::= { dot11RogueStaEntry 9 }

rogueStaAttackStatus		OBJECT-TYPE
				SYNTAX      	TruthValue
				MAX-ACCESS  	read-write
				STATUS      	current
				DESCRIPTION
				      "Whether strategies to the rogue station."
				::= { dot11RogueStaEntry 10 }

rogueStaToIgnore		OBJECT-TYPE
				SYNTAX      	TruthValue
				MAX-ACCESS  	read-write
				STATUS      	current
				DESCRIPTION
				      "Whether or not ignore the rogue Station."
				::= { dot11RogueStaEntry 11 }
				
rogueStaManufacturer		OBJECT-TYPE
				SYNTAX      	DisplayString
				MAX-ACCESS  	read-only
				STATUS      	current
				DESCRIPTION
				      "Rogue station manufacturer."
				::= { dot11RogueStaEntry 12 }				

dot11Service	OBJECT IDENTIFIER ::={ dot11AcGroup 6 }

dot11SnmpServiceTable OBJECT-TYPE
    SYNTAX      SEQUENCE OF Dot11SnmpServiceEntry
    MAX-ACCESS  not-accessible
    STATUS      current
    DESCRIPTION
        "This table shows snmp service information."
    ::= { dot11Service 1 }

dot11SnmpServiceEntry  OBJECT-TYPE
    SYNTAX      Dot11SnmpServiceEntry
    MAX-ACCESS  not-accessible
    STATUS      current
    DESCRIPTION
        "Snmp service information."
    INDEX { communityID }
    ::= { dot11SnmpServiceTable 1 }
   
Dot11SnmpServiceEntry ::=SEQUENCE{
	communityID			INTEGER,
	communityName			DisplayString,
	communityPermission		INTEGER
}
communityID 				OBJECT-TYPE
					SYNTAX      	INTEGER
					MAX-ACCESS  	read-only
					STATUS      	current
					DESCRIPTION
					      "Community ID."
					::= { dot11SnmpServiceEntry 1 }

communityName	 			OBJECT-TYPE
					SYNTAX     	DisplayString 
					MAX-ACCESS 	read-write
					STATUS     	current
					DESCRIPTION
				        	"Community name."
					::= { dot11SnmpServiceEntry 2 }

communityPermission 				OBJECT-TYPE
					SYNTAX      	INTEGER{
							read-only(0),
							read-write(1)
								}
					MAX-ACCESS  	read-write
					STATUS      	current
					DESCRIPTION
					      "Community permission."
					::= { dot11SnmpServiceEntry 3 }

dot11AdministratorTable OBJECT-TYPE
    SYNTAX      SEQUENCE OF Dot11AdministratorEntry
    MAX-ACCESS  not-accessible
    STATUS      current
    DESCRIPTION
        "This table create administrator information."
    ::= { dot11Service 2 }

dot11AdministratorEntry  OBJECT-TYPE
    SYNTAX      Dot11AdministratorEntry
    MAX-ACCESS  not-accessible
    STATUS      current
    DESCRIPTION
        "Create administrator information."
    INDEX { administratorID }
    ::= { dot11AdministratorTable 1 }
   
Dot11AdministratorEntry ::=SEQUENCE{
	administratorID			INTEGER,
	administratorName		DisplayString,
	administratorPassword		DisplayString,
	administratorPrivilege		INTEGER,
	administratorRowStatus		RowStatus
}
administratorID 			OBJECT-TYPE
					SYNTAX      	INTEGER
					MAX-ACCESS  	read-only
					STATUS      	current
					DESCRIPTION
					      "Administrator ID."
					::= { dot11AdministratorEntry 1 }

administratorName	 		OBJECT-TYPE
					SYNTAX     	DisplayString(SIZE(4..32))
					MAX-ACCESS 	read-create
					STATUS     	current
					DESCRIPTION
				        	"Administrator name."
					::= { dot11AdministratorEntry 2 }

administratorPassword 			OBJECT-TYPE
					SYNTAX      	DisplayString(SIZE(6..16))
					MAX-ACCESS  	read-create
					STATUS      	current
					DESCRIPTION
					      "Administrator password."
					::= { dot11AdministratorEntry 3 }
					
administratorPrivilege 			OBJECT-TYPE
					SYNTAX      	INTEGER{
								administrator(1),
								user(2)
							       }
					MAX-ACCESS  	read-create
					STATUS      	current
					DESCRIPTION
					      "Administrator privilege."
					::= { dot11AdministratorEntry 4 }
					
administratorRowStatus			OBJECT-TYPE
				    	SYNTAX      RowStatus
				    	MAX-ACCESS  read-create
				    	STATUS      current
				    	DESCRIPTION
				        	"This variable is used to create, modify, and/or delete a row in this table."
				    	::= { dot11AdministratorEntry 5 }										

dot11VlanConfigTable OBJECT-TYPE
	    SYNTAX      SEQUENCE OF Dot11VlanConfigEntry
	    MAX-ACCESS  not-accessible
	    STATUS      current
	    DESCRIPTION
	        "This table shows vlan ability information."
	    ::= { dot11AcGroup 7 }

dot11VlanConfigEntry  OBJECT-TYPE
    SYNTAX      Dot11VlanConfigEntry
    MAX-ACCESS  not-accessible
    STATUS      current
    DESCRIPTION
        "Vlan ability information."
    INDEX { wlanID }
    ::= { dot11VlanConfigTable 1 }
   
Dot11VlanConfigEntry ::=SEQUENCE{
	wlanID		INTEGER,
	vlanID			INTEGER
}
wlanID	        OBJECT-TYPE
		SYNTAX  INTEGER
		MAX-ACCESS read-write
		STATUS     current
		DESCRIPTION
			"Vlan ID."
			::= { dot11VlanConfigEntry 1 }

vlanID		OBJECT-TYPE
		SYNTAX  INTEGER(2..4094)
		MAX-ACCESS read-write
		STATUS     current
		DESCRIPTION
			"Vlan ID."
			::= { dot11VlanConfigEntry 2 }

dot11WhiteBlackList OBJECT IDENTIFIER ::={ dot11AcGroup 8 }
dot11LegalDeviceTable OBJECT-TYPE
	    SYNTAX      SEQUENCE OF Dot11LegalDeviceEntry
	    MAX-ACCESS  not-accessible
	    STATUS      current
	    DESCRIPTION
	        "This table shows legal device information."
	    ::= { dot11WhiteBlackList 1 }

dot11LegalDeviceEntry  OBJECT-TYPE
    SYNTAX      Dot11LegalDeviceEntry
    MAX-ACCESS  not-accessible
    STATUS      current
    DESCRIPTION
        "Legal device information."
    INDEX { legalMacID }
    ::= { dot11LegalDeviceTable 1 }
   
Dot11LegalDeviceEntry ::=SEQUENCE{
	legalMacID		INTEGER,
	legalMacAddress		DisplayString,
	legalRowStatus		RowStatus
}
legalMacID	OBJECT-TYPE
		SYNTAX  INTEGER
		MAX-ACCESS read-only
		STATUS     current
		DESCRIPTION
			"Legal MAC ID."
			::= { dot11LegalDeviceEntry 1 }

legalMacAddress	OBJECT-TYPE
		SYNTAX  DisplayString
		MAX-ACCESS read-create
		STATUS     current
		DESCRIPTION
			"Legal MAC address."
			::= { dot11LegalDeviceEntry 2 }

legalRowStatus	OBJECT-TYPE
	    	SYNTAX      RowStatus
	    	MAX-ACCESS  read-create
	    	STATUS      current
	    	DESCRIPTION
	        	"This variable is used to create, modify, and/or delete a row
	        	 in this table."
	    	::= { dot11LegalDeviceEntry 3 }

dot11IllegalDeviceTable OBJECT-TYPE
	    SYNTAX      SEQUENCE OF Dot11IllegalDeviceEntry
	    MAX-ACCESS  not-accessible
	    STATUS      current
	    DESCRIPTION
	        "This table shows illegal device information."
	    ::= { dot11WhiteBlackList 2 }

dot11IllegalDeviceEntry  OBJECT-TYPE
    SYNTAX      Dot11IllegalDeviceEntry
    MAX-ACCESS  not-accessible
    STATUS      current
    DESCRIPTION
        "Illegal device information."
    INDEX { blackListDeviceMacID }
    ::= { dot11IllegalDeviceTable 1 }
   
Dot11IllegalDeviceEntry ::=SEQUENCE{
		blackListDeviceMacID	INTEGER,
		blackListDeviceMAC	DisplayString,
		blackListAddReason	DisplayString,
		blackListDuration	Unsigned32,
		blackListAddType	INTEGER,
		IllegalRowStatus	RowStatus
}
blackListDeviceMacID	OBJECT-TYPE
			SYNTAX  INTEGER
			MAX-ACCESS read-only
			STATUS     current
			DESCRIPTION
				"Black list MAC ID."
			::= { dot11IllegalDeviceEntry 1 }

blackListDeviceMAC	OBJECT-TYPE
			SYNTAX  DisplayString
			MAX-ACCESS read-create
			STATUS     current
			DESCRIPTION
				"Black list MAC address."
			::= { dot11IllegalDeviceEntry 2 }

blackListAddReason	OBJECT-TYPE
			SYNTAX  DisplayString
			MAX-ACCESS read-only
			STATUS     current
			DESCRIPTION
				" The reason why add to black list."
			::= { dot11IllegalDeviceEntry 3 }

blackListDuration	OBJECT-TYPE
			SYNTAX  Unsigned32
			MAX-ACCESS read-only
			STATUS     current
			DESCRIPTION
				" How long it keeps in black list."
			::= { dot11IllegalDeviceEntry 4 }

blackListAddType	OBJECT-TYPE
			SYNTAX  INTEGER{
				static(1),
				dynamic(2)
					}
			MAX-ACCESS read-only
			STATUS     current
			DESCRIPTION
				" Black list add type."
			::= { dot11IllegalDeviceEntry 5 }
			
IllegalRowStatus	OBJECT-TYPE
	    		SYNTAX      RowStatus
	    		MAX-ACCESS  read-create
	    		STATUS      current
	    		DESCRIPTION
	        		"This variable is used to create, modify, and/or delete a row
	        	 	in this table."
	    		::= { dot11IllegalDeviceEntry 6 }			


dot11NewIllegalDeviceTable OBJECT-TYPE
	    SYNTAX      SEQUENCE OF Dot11NewIllegalDeviceEntry
	    MAX-ACCESS  not-accessible
	    STATUS      current
	    DESCRIPTION
	        "This table shows illegal device information."
	    ::= { dot11WhiteBlackList 3 }

dot11NewIllegalDeviceEntry  OBJECT-TYPE
    SYNTAX      Dot11NewIllegalDeviceEntry
    MAX-ACCESS  not-accessible
    STATUS      current
    DESCRIPTION
        "Illegal device information."
    INDEX { NewblackListDeviceMacID }
    ::= { dot11NewIllegalDeviceTable 1 }
   
Dot11NewIllegalDeviceEntry ::=SEQUENCE{
		NewblackListDeviceMacID	INTEGER,
		NewblackListDeviceMAC	DisplayString,
		NewblackListAddReason	DisplayString,
		NewblackListDuration	Unsigned32,
		NewblackListAddType	INTEGER
}
NewblackListDeviceMacID	OBJECT-TYPE
			SYNTAX  INTEGER
			MAX-ACCESS read-only
			STATUS     current
			DESCRIPTION
				"Black list MAC ID."
			::= { dot11NewIllegalDeviceEntry 1 }

NewblackListDeviceMAC	OBJECT-TYPE
			SYNTAX  DisplayString
			MAX-ACCESS read-only
			STATUS     current
			DESCRIPTION
				"Black list MAC address."
			::= { dot11NewIllegalDeviceEntry 2 }

NewblackListAddReason	OBJECT-TYPE
			SYNTAX  DisplayString
			MAX-ACCESS read-only
			STATUS     current
			DESCRIPTION
				" The reason why add to black list."
			::= { dot11NewIllegalDeviceEntry 3 }

NewblackListDuration	OBJECT-TYPE
			SYNTAX  Unsigned32
			MAX-ACCESS read-only
			STATUS     current
			DESCRIPTION
				" How long it keeps in black list."
			::= { dot11NewIllegalDeviceEntry 4 }

NewblackListAddType	OBJECT-TYPE
			SYNTAX  INTEGER{
				static(1),
				dynamic(2)
					}
			MAX-ACCESS read-only
			STATUS     current
			DESCRIPTION
				" Black list add type."
			::= { dot11NewIllegalDeviceEntry 5 }
			
dot11TerminalBlackListTable OBJECT-TYPE
	    SYNTAX      SEQUENCE OF Dot11TerminalBlackListEntry
	    MAX-ACCESS  not-accessible
	    STATUS      current
	    DESCRIPTION
	        "This table shows black list information of terminal."
	    ::= { dot11WhiteBlackList 4 }

dot11TerminalBlackListEntry  OBJECT-TYPE
    SYNTAX      Dot11TerminalBlackListEntry
    MAX-ACCESS  not-accessible
    STATUS      current
    DESCRIPTION
        "Terminal black list information."
    INDEX { TerminalBlackListMAC }
    ::= { dot11TerminalBlackListTable 1 }
   
Dot11TerminalBlackListEntry ::=SEQUENCE{
		TerminalBlackListMAC		DisplayString,
		TerminalBlackListAddReason	DisplayString,
		TerminalBlackListDuration	Unsigned32,
		BlackListRowStatus		RowStatus
}	
TerminalBlackListMAC	OBJECT-TYPE
			SYNTAX  DisplayString
			MAX-ACCESS read-only
			STATUS     current
			DESCRIPTION
				"Black list terminal MAC address."
			::= { dot11TerminalBlackListEntry 1 }
TerminalBlackListAddReason	OBJECT-TYPE
			SYNTAX  DisplayString
			MAX-ACCESS read-only
			STATUS     current
			DESCRIPTION
				" The reason why add to black list."
			::= { dot11TerminalBlackListEntry 2 }
TerminalBlackListDuration	OBJECT-TYPE
			SYNTAX  Unsigned32
			MAX-ACCESS read-only
			STATUS     current
			DESCRIPTION
				" How long it keeps in black list."
			::= { dot11TerminalBlackListEntry 3 }
BlackListRowStatus	OBJECT-TYPE
	    		SYNTAX      RowStatus
	    		MAX-ACCESS  read-create
	    		STATUS      current
	    		DESCRIPTION
	        		"This variable is used to create, modify, and/or delete a row
	        	 	in this table."
	    		::= { dot11TerminalBlackListEntry 4 }				
	    		
dot11TerminalWhiteListTable OBJECT-TYPE
	    SYNTAX      SEQUENCE OF dot11TerminalWhiteListEntry
	    MAX-ACCESS  not-accessible
	    STATUS      current
	    DESCRIPTION
	        "This table shows White list information of terminal."
	    ::= { dot11WhiteBlackList 5 }

dot11TerminalWhiteListEntry  OBJECT-TYPE
    SYNTAX      dot11TerminalWhiteListEntry
    MAX-ACCESS  not-accessible
    STATUS      current
    DESCRIPTION
        "Terminal White list information."
    INDEX { TerminalWhiteListMAC }
    ::= { dot11TerminalWhiteListTable 1 }
   
dot11TerminalWhiteListEntry ::=SEQUENCE{
		TerminalWhiteListMAC		DisplayString,
		WhiteListRowStatus		RowStatus
}	
TerminalWhiteListMAC	OBJECT-TYPE
			SYNTAX  DisplayString
			MAX-ACCESS read-only
			STATUS     current
			DESCRIPTION
				"White list terminal MAC address."
			::= { dot11TerminalWhiteListEntry 1 }

WhiteListRowStatus	OBJECT-TYPE
	    		SYNTAX      RowStatus
	    		MAX-ACCESS  read-create
	    		STATUS      current
	    		DESCRIPTION
	        		"This variable is used to create, modify, and/or delete a row
	        	 	in this table."
	    		::= { dot11TerminalWhiteListEntry 2 }	    		

dot11PermitConfigTable OBJECT-TYPE
	    SYNTAX      SEQUENCE OF Dot11PermitConfigEntry
	    MAX-ACCESS  not-accessible
	    STATUS      current
	    DESCRIPTION
	        "This table shows productor config permission information."
	    ::= { dot11AcGroup 9 }

dot11PermitConfigEntry  OBJECT-TYPE
    SYNTAX      Dot11PermitConfigEntry
    MAX-ACCESS  not-accessible
    STATUS      current
    DESCRIPTION
        "Productor config permission information."
    INDEX { permitConfigID }
    ::= { dot11PermitConfigTable 1 }
   
Dot11PermitConfigEntry ::=SEQUENCE{
	permitConfigID		INTEGER,
	permitConfig		DisplayString,
	permitConfigRowStatus	RowStatus
}
permitConfigID		OBJECT-TYPE
			SYNTAX  INTEGER
			MAX-ACCESS read-only
			STATUS     current
			DESCRIPTION
				"Config permission ID."
			::= { dot11PermitConfigEntry 1 }

permitConfig		OBJECT-TYPE
			SYNTAX  DisplayString
			MAX-ACCESS read-create
			STATUS     current
			DESCRIPTION
				"Config permission,the format is like xx:xx:xx. If the input format didn't match this format,the permitConfig will not be set"
			::= { dot11PermitConfigEntry 2 }

permitConfigRowStatus	OBJECT-TYPE
		    	SYNTAX      RowStatus
		    	MAX-ACCESS  read-create
		    	STATUS      current
		    	DESCRIPTION
		        	"This variable is used to create, modify, and/or delete a row
		        	 in this table."
		    	::= { dot11PermitConfigEntry 3 }

dot11PermitSSIDTable OBJECT-TYPE
	    SYNTAX      SEQUENCE OF Dot11PermitSSIDEntry
	    MAX-ACCESS  not-accessible
	    STATUS      current
	    DESCRIPTION
	        "This table shows SSID config permission information."
	    ::= { dot11AcGroup 10 }

dot11PermitSSIDEntry  OBJECT-TYPE
    SYNTAX      Dot11PermitSSIDEntry
    MAX-ACCESS  not-accessible
    STATUS      current
    DESCRIPTION
        "SSID config permission information."
    INDEX { permitSSIDID }
    ::= { dot11PermitSSIDTable 1 }
   
Dot11PermitSSIDEntry ::=SEQUENCE{
	permitSSIDID		INTEGER,
	permitSSID		DisplayString,
	permitSSIDRowStatus	RowStatus
}
permitSSIDID		OBJECT-TYPE
			SYNTAX  INTEGER
			MAX-ACCESS read-only
			STATUS     current
			DESCRIPTION
				"SSID permission ID."
			::= { dot11PermitSSIDEntry 1 }

permitSSID		OBJECT-TYPE
			SYNTAX  DisplayString
			MAX-ACCESS read-create
			STATUS     current
			DESCRIPTION
				"SSID config permission."
			::= { dot11PermitSSIDEntry 2 }

permitSSIDRowStatus	OBJECT-TYPE
		    	SYNTAX      RowStatus
		    	MAX-ACCESS  read-create
		    	STATUS      current
		    	DESCRIPTION
		        	"This variable is used to create, modify, and/or delete a row
		        	 in this table."
		    	::= { dot11PermitSSIDEntry 3 }

dot11Attack OBJECT IDENTIFIER ::={ dot11AcGroup 11 }
dot11AttackMACTable OBJECT-TYPE
	    SYNTAX      SEQUENCE OF Dot11AttackMACEntry
	    MAX-ACCESS  not-accessible
	    STATUS      current
	    DESCRIPTION
	        "This table shows MAC attack information."
	    ::= { dot11Attack 1 }

dot11AttackMACEntry  OBJECT-TYPE
    SYNTAX      Dot11AttackMACEntry
    MAX-ACCESS  not-accessible
    STATUS      current
    DESCRIPTION
        "MAC attack information."
    INDEX { attackMACID }
    ::= { dot11AttackMACTable 1 }
   
Dot11AttackMACEntry ::=SEQUENCE{
	attackMACID		INTEGER,
	attackMAC		DisplayString,
	attackMACRowStatus	RowStatus
}
attackMACID		OBJECT-TYPE
			SYNTAX  INTEGER
			MAX-ACCESS read-only
			STATUS     current
			DESCRIPTION
				"MAC attack ID."
			::= { dot11AttackMACEntry 1 }

attackMAC		OBJECT-TYPE
			SYNTAX  DisplayString
			MAX-ACCESS read-create
			STATUS     current
			DESCRIPTION
				"MAC attack."
			::= { dot11AttackMACEntry 2 }

attackMACRowStatus	OBJECT-TYPE
		    	SYNTAX      RowStatus
		    	MAX-ACCESS  read-create
		    	STATUS      current
		    	DESCRIPTION
		        	"This variable is used to create, modify, and/or delete a row
		        	 in this table."
		    	::= { dot11AttackMACEntry 3 }

-- **********************************************************************
-- * dot11WIDPolicy
-- **********************************************************************

dot11WIDPolicy			OBJECT IDENTIFIER ::={ dot11Attack 2}
				
widsFloodInterval		OBJECT-TYPE
				SYNTAX  Unsigned32(1..5)
				MAX-ACCESS read-write
				STATUS     current
				DESCRIPTION
					"Flooding attack detection Statistics Length."
				::= { dot11WIDPolicy 1 }

widsBlackListThreshold		OBJECT-TYPE
				SYNTAX  Unsigned32(1..100)
				MAX-ACCESS read-write
				STATUS     current
				DESCRIPTION
					"Threshold blacklist."
				::= { dot11WIDPolicy 2 }

widsBlackListDuration		OBJECT-TYPE
				SYNTAX  Unsigned32(1..36000)
				MAX-ACCESS read-write
				STATUS     current
				DESCRIPTION
					"The duration of staying in blacklist."
				::= { dot11WIDPolicy 3 }				

widsFloodDetectOnOff		OBJECT-TYPE
				SYNTAX  INTEGER{
						off(0),
						on(1)
						}
				MAX-ACCESS read-write
				STATUS     current
				DESCRIPTION
					"Flooding attack detection switch."
				::= { dot11WIDPolicy 4 }
	
SSIDFilterOnOff			OBJECT-TYPE
				SYNTAX  INTEGER{
						off(0),
						on(1)
						}
				MAX-ACCESS read-write
				STATUS     current
				DESCRIPTION
					"SSID name filter switch."
				::= { dot11WIDPolicy 5 }

BSSIDFilterOnOff		OBJECT-TYPE
				SYNTAX  INTEGER{
						off(0),
						on(1)
						}
				MAX-ACCESS read-write
				STATUS     current
				DESCRIPTION
					"BSSID filter switch."
				::= { dot11WIDPolicy 6 }
			
RogueAPCountermeasureSwitch	OBJECT-TYPE
				SYNTAX  INTEGER{
						enable(1),
						disable(2)
						}
				MAX-ACCESS read-write
				STATUS     current
				DESCRIPTION
					"Rogue AP Countermeasure Switch."
				::= { dot11WIDPolicy 7 }
				
RogueAPCountermeasureMode	OBJECT-TYPE
				SYNTAX  INTEGER{
						ap(1),
						adhoc(2),
						all(3)
						}
				MAX-ACCESS read-write
				STATUS     current
				DESCRIPTION
					"Rogue AP Countermeasure Mode."
				::= { dot11WIDPolicy 8 }								
				
								


dot11wtpConfig OBJECT IDENTIFIER ::={ dot11AcGroup 12 }
dot11wlanConfig OBJECT IDENTIFIER ::={ dot11AcGroup 13 }
dot11securityConfig OBJECT IDENTIFIER ::={ dot11AcGroup 14 }

dot11CreateWtpTable OBJECT-TYPE
	    SYNTAX      SEQUENCE OF Dot11CreateWtpEntry
	    MAX-ACCESS  not-accessible
	    STATUS      current
	    DESCRIPTION
	        "This table create AP."
	    ::= { dot11wtpConfig 1 }

dot11CreateWtpEntry  OBJECT-TYPE
    SYNTAX      Dot11CreateWtpEntry
    MAX-ACCESS  not-accessible
    STATUS      current
    DESCRIPTION
        "Create AP."
    INDEX { wtpMac }
    ::= { dot11CreateWtpTable 1 }
   
Dot11CreateWtpEntry ::=SEQUENCE{
	wtpID			INTEGER,
	wtpName			DisplayString,
	wtpModel		DisplayString,
	wtpMac		DisplayString,
	wtpRowStatus		RowStatus
}
wtpID			OBJECT-TYPE
			SYNTAX  INTEGER
			MAX-ACCESS read-create
			STATUS     current
			DESCRIPTION
				"Create AP ID."
			::= { dot11CreateWtpEntry 1 }

wtpName			OBJECT-TYPE
			SYNTAX  DisplayString(SIZE(1..15))
			MAX-ACCESS read-create
			STATUS     current
			DESCRIPTION
				"AP name."
			::= { dot11CreateWtpEntry 2 }

wtpModel		OBJECT-TYPE
			SYNTAX  DisplayString
			MAX-ACCESS read-create
			STATUS     current
			DESCRIPTION
				"AP model."
			::= { dot11CreateWtpEntry 3 }

wtpMac		OBJECT-TYPE
			SYNTAX  DisplayString(SIZE(20))
			MAX-ACCESS read-create
			STATUS     current
			DESCRIPTION
				"AP mac."
			::= { dot11CreateWtpEntry 4 }

wtpRowStatus	OBJECT-TYPE
		    	SYNTAX      RowStatus
		    	MAX-ACCESS  read-create
		    	STATUS      current
		    	DESCRIPTION
		        	"This variable is used to create, modify, and/or delete a row
		        	 in this table."
		    	::= { dot11CreateWtpEntry 5 }
dot11ConfigWtpTable OBJECT-TYPE
	    SYNTAX      SEQUENCE OF Dot11ConfigWtpEntry
	    MAX-ACCESS  not-accessible
	    STATUS      current
	    DESCRIPTION
	        "This table config wtp."
	    ::= { dot11wtpConfig 2 }

dot11ConfigWtpEntry  OBJECT-TYPE
    SYNTAX      Dot11ConfigWtpEntry
    MAX-ACCESS  not-accessible
    STATUS      current
    DESCRIPTION
        "Config wtp."
    INDEX { wtpID }
    ::= { dot11ConfigWtpTable 1 }
   
Dot11ConfigWtpEntry ::=SEQUENCE{
	wtpBindPort			DisplayString,
	wtpBindWlan			DisplayString,
	wtpUsed				INTEGER,
	wtpMaxStaNum			INTEGER,
	wtpLoadBalanceTrigerBaseUsr	INTEGER,
	wtpLoadBalanceTrigerBaseFlow	INTEGER,
	wtpRadioPrioritySelect		INTEGER
}
wtpBindPort		OBJECT-TYPE
			SYNTAX  DisplayString
			MAX-ACCESS read-write
			STATUS     current
			DESCRIPTION
				"Bind port."
			::= { dot11ConfigWtpEntry 1 }

wtpBindWlan		OBJECT-TYPE
			SYNTAX  DisplayString
			MAX-ACCESS read-only
			STATUS     current
			DESCRIPTION
				"Bind wlan."
			::= { dot11ConfigWtpEntry 2 }

wtpUsed			OBJECT-TYPE
			SYNTAX  INTEGER{
				used(1),
				unused(0)
					}
			MAX-ACCESS read-write
			STATUS     current
			DESCRIPTION
				"AP whether used."
			::= { dot11ConfigWtpEntry 3 }

wtpMaxStaNum		OBJECT-TYPE
			SYNTAX  INTEGER(0..32767)
			MAX-ACCESS read-write
			STATUS     current
			DESCRIPTION
				"Max station number."
			::= { dot11ConfigWtpEntry 4 }

wtpLoadBalanceTrigerBaseUsr	OBJECT-TYPE
			SYNTAX  INTEGER(1..64)
			MAX-ACCESS read-write
			STATUS     current
			DESCRIPTION
				"Load balance base on user."
			::= { dot11ConfigWtpEntry 5 }

wtpLoadBalanceTrigerBaseFlow	OBJECT-TYPE
			SYNTAX  INTEGER(0..1024)
			MAX-ACCESS read-write
			STATUS     current
			DESCRIPTION
				"Load balance base on user."
			::= { dot11ConfigWtpEntry 6 }

wtpRadioPrioritySelect	OBJECT-TYPE
			SYNTAX  INTEGER{
                                       Low(0),
                                       High(1)
					} 
			MAX-ACCESS read-write
			STATUS     current
			DESCRIPTION
				"Select Radio Priority,low is 2.4G,and high is 5.8G."
			::= { dot11ConfigWtpEntry 7 }

dot11SSIDVlanTable OBJECT-TYPE
	    SYNTAX      SEQUENCE OF Dot11SSIDVlanEntry
	    MAX-ACCESS  not-accessible
	    STATUS      current
	    DESCRIPTION
	        "This table shows SSID stats information."
	    ::= { dot11wtpConfig 3 }
dot11SSIDVlanEntry  OBJECT-TYPE
    SYNTAX      Dot11SSIDVlanEntry
    MAX-ACCESS  not-accessible
    STATUS      current
    DESCRIPTION
        "SSID Config information."
    INDEX { wtpId,
		wlanId }
    ::= { dot11SSIDVlanTable 1 }
   
Dot11SSIDVlanEntry ::=SEQUENCE{
                wtpId                           INTEGER,
		wlanId				INTEGER,
		VlanId	 		        INTEGER,
                VlanRowStatus                   RowStatus,
                wtpMacAddress                   DisplayString,
                wlanSSID                        DisplayString
	
}
wtpId				OBJECT-TYPE
				SYNTAX  INTEGER
				MAX-ACCESS read-create
				STATUS     current
				DESCRIPTION
					"Set wtpId."
				::= { dot11SSIDVlanEntry 1 }
				
wlanId				OBJECT-TYPE
				SYNTAX  INTEGER
				MAX-ACCESS read-create
				STATUS     current
				DESCRIPTION
					"Set wlanCurrID Id."
				::= { dot11SSIDVlanEntry 2 }
				
VlanId				OBJECT-TYPE
				SYNTAX  INTEGER
				MAX-ACCESS read-write
				STATUS     current
				DESCRIPTION
					"Set Vlan Id."
				::= { dot11SSIDVlanEntry 3 }
VlanRowStatus	                OBJECT-TYPE
		    	        SYNTAX      RowStatus
		    	        MAX-ACCESS  read-create
		    	        STATUS      current
		         	DESCRIPTION
		        	"This variable is used to create, modify, and/or delete a row
		        	 in this table."
		    	        ::= { dot11SSIDVlanEntry 4 }
wtpMacAddress			OBJECT-TYPE
				SYNTAX  DisplayString
				MAX-ACCESS read-only
				STATUS     current
				DESCRIPTION
					"wtpMacAddress."
				::= { dot11SSIDVlanEntry 5 }
wlanSSID			OBJECT-TYPE
				SYNTAX  DisplayString
				MAX-ACCESS read-only
				STATUS     current
				DESCRIPTION
					"wlanSSID."
				::= { dot11SSIDVlanEntry 6 }


dot11SSIDBindTable OBJECT-TYPE
	    SYNTAX      SEQUENCE OF Dot11SSIDBindEntry
	    MAX-ACCESS  not-accessible
	    STATUS      current
	    DESCRIPTION
	        "This table shows SSIDBind information."
	    ::= { dot11wtpConfig 4 }
dot11SSIDBindEntry  OBJECT-TYPE
    SYNTAX      Dot11SSIDBindEntry
    MAX-ACCESS  not-accessible
    STATUS      current
    DESCRIPTION
        "SSID BindWlan information."
    INDEX { NewWtpMac,
		NewInterface, 
                NewWlanId }
    ::= { dot11SSIDBindTable 1 }
   
Dot11SSIDBindEntry ::=SEQUENCE{
                NewWtpMac                       DisplayString,
		NewInterface			INTEGER,
		NewWlanId		        INTEGER,
                BssIDMac                        PhysAddress,
                BssIDBindRowStatus              RowStatus	
}
NewWtpMac		        OBJECT-TYPE
				SYNTAX  DisplayString
				MAX-ACCESS read-only
				STATUS     current
				DESCRIPTION
					" wtpMac."
				::= { dot11SSIDBindEntry 1 }
				
NewInterface	                OBJECT-TYPE
				SYNTAX   INTEGER
				MAX-ACCESS read-only
				STATUS     current
				DESCRIPTION
					"Interface."
				::= { dot11SSIDBindEntry 2 }
				
NewWlanId			OBJECT-TYPE
				SYNTAX  INTEGER
				MAX-ACCESS read-only
				STATUS     current
				DESCRIPTION
					"wlanId."
				::= { dot11SSIDBindEntry 3 }

BssIDMac	                OBJECT-TYPE
		    	        SYNTAX      PhysAddress
		    	        MAX-ACCESS  read-only
		    	        STATUS      current
		         	DESCRIPTION
		        	"BssIDMac."
		    	        ::= { dot11SSIDBindEntry 4 }
BssIDBindRowStatus	        OBJECT-TYPE
		    	        SYNTAX      RowStatus
		    	        MAX-ACCESS  read-create
		    	        STATUS      current
		         	DESCRIPTION
		        	"BssIDMac."
		    	        ::= { dot11SSIDBindEntry 5 }






dot11RWVlanTable OBJECT-TYPE
	    SYNTAX      SEQUENCE OF dot11RWVlanEntry
	    MAX-ACCESS  not-accessible
	    STATUS      current
	    DESCRIPTION
	        "This table shows vlan stats information."
	    ::= { dot11wtpConfig 5 }
dot11RWVlanEntry  OBJECT-TYPE
    SYNTAX        dot11RWVlanEntry
    MAX-ACCESS    not-accessible
    STATUS        current
    DESCRIPTION
        "Vlan Config information."
    INDEX { wtpMacAddr,
              RadioLoID,
		wlanId }
    ::= { dot11RWVlanTable 1 }
   
dot11RWVlanEntry ::=SEQUENCE{

		    RadioLoID                           INTEGER,
		    RWVlanId	 		        INTEGER

                
	
}


RadioLoID			OBJECT-TYPE
				SYNTAX  INTEGER
				MAX-ACCESS read-write
				STATUS     current
				DESCRIPTION
					"RadioLoID Id."
				::= { dot11RWVlanEntry 1 }
				
RWVlanId			OBJECT-TYPE
				SYNTAX  INTEGER
				MAX-ACCESS read-write
				STATUS     current
				DESCRIPTION
					"Set VlanId Id."
				::= { dot11RWVlanEntry 2 }








dot11CreateWlanTable OBJECT-TYPE
	    SYNTAX      SEQUENCE OF Dot11CreateWlanEntry
	    MAX-ACCESS  not-accessible
	    STATUS      current
	    DESCRIPTION
	        "This table create wlan."
	    ::= { dot11wlanConfig 1 }

dot11CreateWlanEntry  OBJECT-TYPE
    SYNTAX      Dot11CreateWlanEntry
    MAX-ACCESS  not-accessible
    STATUS      current
    DESCRIPTION
        "Create wlan."
    INDEX { wlanID }
    ::= { dot11CreateWlanTable 1 }
   
Dot11CreateWlanEntry ::=SEQUENCE{
	wlanName		DisplayString,
	wlanESSID		DisplayString,
	wlanRowStatus		RowStatus
}

wlanName		OBJECT-TYPE
			SYNTAX  DisplayString(SIZE(1..15))
			MAX-ACCESS read-create
			STATUS     current
			DESCRIPTION
				"Wlan name."
			::= { dot11CreateWlanEntry 1 }

wlanESSID		OBJECT-TYPE
			SYNTAX  DisplayString(SIZE(1..32))
			MAX-ACCESS read-create
			STATUS     current
			DESCRIPTION
				"ESSID."
			::= { dot11CreateWlanEntry 2 }

wlanRowStatus		OBJECT-TYPE
		    	SYNTAX      RowStatus
		    	MAX-ACCESS  read-create
		    	STATUS      current
		    	DESCRIPTION
		        	"This variable is used to create, modify, and/or delete a row
		        	 in this table."
		    	::= { dot11CreateWlanEntry 3 }

dot11ConfigWlanTable OBJECT-TYPE
	    SYNTAX      SEQUENCE OF Dot11ConfigWlanEntry
	    MAX-ACCESS  not-accessible
	    STATUS      current
	    DESCRIPTION
	        "This table config wlan."
	    ::= { dot11wlanConfig 2 }

dot11ConfigWlanEntry  OBJECT-TYPE
    SYNTAX      Dot11ConfigWlanEntry
    MAX-ACCESS  not-accessible
    STATUS      current
    DESCRIPTION
        "Configwlan."
    INDEX { wlanID }
    ::= { dot11ConfigWlanTable 1 }
   
Dot11ConfigWlanEntry ::=SEQUENCE{
	wlanBindSecurity			INTEGER,
	wlanBindIf				DisplayString,
	wlanHideEssid				INTEGER,
	wlanServiceEnable			INTEGER,
	wlanMaxConnectUsr			INTEGER,
	wlanLoadBalanceStatus			INTEGER,
	wlanLoadBalanceStatusBaseOnFlow		INTEGER,
	wlanLoadBalanceStatusBaseOnUsr		INTEGER,
	wlanLoadBalanceStatusEnable		INTEGER,
	wlanLoadBalanceTrafficDiffThreshhd	INTEGER,
	wlanLoadBalanceUsersDiffThreshhd	INTEGER,
	wlanStaOnlineNum			INTEGER,
	wlanUsrWirelessResoUseRate		DisplayString,
	wlanBindSecType				INTEGER,
	wlanBindEncryType			INTEGER,
	wlanInterfaceIPAddr			DisplayString
}
wlanBindSecurity			OBJECT-TYPE
					SYNTAX  INTEGER
					MAX-ACCESS read-write
					STATUS     current
					DESCRIPTION
						"Bind security."
					::= { dot11ConfigWlanEntry 1 }

wlanBindIf				OBJECT-TYPE
					SYNTAX  DisplayString
					MAX-ACCESS read-write
					STATUS     current
					DESCRIPTION
						"Bind interface."
					::= { dot11ConfigWlanEntry 2 }

wlanHideEssid				OBJECT-TYPE
					SYNTAX  INTEGER{
							yes(1),
							no(0)
							}
					MAX-ACCESS read-write
					STATUS     current
					DESCRIPTION
						"Hide ESSID."
					::= { dot11ConfigWlanEntry 3 }

wlanServiceEnable			OBJECT-TYPE
					SYNTAX  INTEGER{
							enable(1),
							disable(0)
							}
					MAX-ACCESS read-write
					STATUS     current
					DESCRIPTION
						"Service enable."
					::= { dot11ConfigWlanEntry 4 }

wlanMaxConnectUsr			OBJECT-TYPE
					SYNTAX  INTEGER(0..65535)
					MAX-ACCESS read-write
					STATUS     current
					DESCRIPTION
						"Max connect user."
					::= { dot11ConfigWlanEntry 5 }

wlanLoadBalanceStatus			OBJECT-TYPE
					SYNTAX  INTEGER{
							no(0),
							number(1),
							flow(2)
							}
					MAX-ACCESS read-write
					STATUS     current
					DESCRIPTION
						"Load balance status."
					::= { dot11ConfigWlanEntry 6 }

wlanLoadBalanceStatusBaseOnFlow		OBJECT-TYPE
					SYNTAX  INTEGER{
							disable(0),
							enable(1)
							}
					MAX-ACCESS read-write
					STATUS     current
					DESCRIPTION
						"Load balance status select.(Base on flow)"
					::= { dot11ConfigWlanEntry 7 }

wlanLoadBalanceStatusBaseOnUsr		OBJECT-TYPE
					SYNTAX  INTEGER{
							disable(0),
							enable(1)
							}
					MAX-ACCESS read-write
					STATUS     current
					DESCRIPTION
						"Load balance status select.(Base on user)"
					::= { dot11ConfigWlanEntry 8 }

wlanLoadBalanceTrafficDiffThreshhd	OBJECT-TYPE
					SYNTAX  INTEGER
					MAX-ACCESS read-write
					STATUS     current
					DESCRIPTION
						"The threshold of flow difference."
					::= { dot11ConfigWlanEntry 9 }

wlanLoadBalanceUsersDiffThreshhd	OBJECT-TYPE
					SYNTAX  INTEGER
					MAX-ACCESS read-write
					STATUS     current
					DESCRIPTION
						"The threshold of user difference."
					::= { dot11ConfigWlanEntry 10 }
wlanStaOnlineNum			OBJECT-TYPE
					SYNTAX  INTEGER
					MAX-ACCESS read-only
					STATUS     current
					DESCRIPTION
						"The num station on wlan."
					::= { dot11ConfigWlanEntry 11 }	
					

wlanUsrWirelessResoUseRate		OBJECT-TYPE
					SYNTAX  DisplayString
					MAX-ACCESS read-only
					STATUS     current
					DESCRIPTION
						"The available rate of resources in the user side.(Wireless side)"
					::= { dot11ConfigWlanEntry 12 }	
					
wlanBindSecType	 			OBJECT-TYPE
					SYNTAX     INTEGER{
							openSystem(1),
							sharedKey(2),
							dot11x(3),
							WPA-P(4),
							WPA2-P(5),
							WPA-E(6),
							WPA2-E(7),
							MD5(8),
							WAPI-PSK(9),
							WAPI-AUTH(10)
							}
					MAX-ACCESS read-only
					STATUS     current
					DESCRIPTION
				        	"The secyurity type of essid."
					::= { dot11ConfigWlanEntry 13 }
					
wlanBindEncryType			OBJECT-TYPE
					SYNTAX    INTEGER{
							none(1),
							wep(2),
							aes(3),
							tkip(4),
							sms4(5)
							}
					MAX-ACCESS read-only
					STATUS     current
					DESCRIPTION
						"The encryption type of essid.
						 Different security type support different encryption type:
						 openSystem:none,wep
						 sharedKey:wep
						 dot11x:wep
						 WPA-E:aes,tkip
						 WPA-P:aes,tkip
						 WPA2-E:aes,tkip
						 WPA2-P:aes,tkip
						 MD5:none
						 WAPI_PSK:sms4
						 WAPI_AUTH:sms4.
						 Security type must suit for encryption type,otherwise the value will not be set."
					::= { dot11ConfigWlanEntry 14 }		

wlanInterfaceIPAddr		OBJECT-TYPE
					SYNTAX  DisplayString
					MAX-ACCESS read-write
					STATUS     current
					DESCRIPTION
						"interface wlan, and config wlan ipaddr. format: 10.1.1.1/24"
					::= { dot11ConfigWlanEntry 15 }							
					
dot11WlanStationTable OBJECT-TYPE
	    SYNTAX      SEQUENCE OF Dot11WlanStaEntry
	    MAX-ACCESS  not-accessible
	    STATUS      current
	    DESCRIPTION
	        "This table config wlan."
	    ::= { dot11wlanConfig 3 }
	    
dot11WlanStaEntry  OBJECT-TYPE
    SYNTAX      Dot11WlanStaEntry
    MAX-ACCESS  not-accessible
    STATUS      current
    DESCRIPTION
        "wlan station."
    INDEX { wlanID,
    		StaMacAddr}
    ::= { dot11WlanStationTable 1 }				  	
 	
Dot11WlanStaEntry ::=SEQUENCE{
	StaMacAddr				DisplayString,
	StaOnlineTime				TimeTicks,
	StaAccessTime				DisplayString,
	StaUplinkTrafficLimitThreshold		Integer32,
	StaDownlinkTrafficLimitThreshold	Integer32,
	StaUplinkBitRate			Counter64,
	StaDownlinkBitRate			Counter64
}			 

StaMacAddr				OBJECT-TYPE
					SYNTAX  DisplayString
					MAX-ACCESS read-only
					STATUS     current
					DESCRIPTION
						"The  station mac address."
					::= { dot11WlanStaEntry  1 }
					
StaOnlineTime				OBJECT-TYPE
					SYNTAX  TimeTicks
					MAX-ACCESS read-only
					STATUS     current
					DESCRIPTION
						"The  station on line time ."
					::= { dot11WlanStaEntry  2 }
					
StaAccessTime				OBJECT-TYPE
					SYNTAX  DisplayString
					MAX-ACCESS read-only
					STATUS     current
					DESCRIPTION
						"The station Access Time."
					::= { dot11WlanStaEntry  3 }
				
StaUplinkTrafficLimitThreshold		OBJECT-TYPE
					SYNTAX     Integer32 
					MAX-ACCESS read-write
					STATUS     current
					DESCRIPTION
				        	"Station uplink traffic limit threshold."
					::= { dot11WlanStaEntry 4 }	
				
StaDownlinkTrafficLimitThreshold	OBJECT-TYPE
					SYNTAX     Integer32 
					MAX-ACCESS read-write
					STATUS     current
					DESCRIPTION
				        	"Station downlink traffic limit threshold."
					::= { dot11WlanStaEntry 5 }
					
StaUplinkBitRate			OBJECT-TYPE
					SYNTAX     Counter64 
					MAX-ACCESS read-only
					STATUS     current
					DESCRIPTION
				        	"Station uplink traffic bit rate."
					::= { dot11WlanStaEntry 6 }	
				
StaDownlinkBitRate			OBJECT-TYPE
					SYNTAX     Counter64 
					MAX-ACCESS read-only
					STATUS     current
					DESCRIPTION
				        	"Station downlink traffic bit rate."
					::= { dot11WlanStaEntry 7 }					
										
dot11WlanStatsTable	OBJECT-TYPE
	    SYNTAX      SEQUENCE OF Dot11WlanStatsEntry
	    MAX-ACCESS  not-accessible
	    STATUS      current
	    DESCRIPTION
	        "This table config wlan."
	    ::= { dot11wlanConfig 4 }
	    
dot11WlanStatsEntry  OBJECT-TYPE
    SYNTAX      Dot11WlanStatsEntry
    MAX-ACCESS  not-accessible
    STATUS      current
    DESCRIPTION
        "wlan status infomation."
    INDEX { wlanID}
    ::= { dot11WlanStatsTable 1 }	
	
Dot11WlanStatsEntry ::=SEQUENCE{
	wlanAssocedStaNum			Counter32,
	wlanAssocReqTimes			Counter32,
	wlanAssocRespTimes			Counter32,
	wlanAssocSuccessTimes			Counter32,
	wlanAssocFailTimes			Counter32,
	wlanUnassocNormallyTimes		Counter32,
	wlanUnassocAnomalyTimes			Counter32
	
}		
wlanAssocedStaNum		OBJECT-TYPE
				SYNTAX  Counter32
				MAX-ACCESS read-only
				STATUS     current
				DESCRIPTION
					"The  total ssociated station numbers."
				::= { dot11WlanStatsEntry  1 }
wlanAssocReqTimes		OBJECT-TYPE
				SYNTAX  Counter32
				MAX-ACCESS read-only
				STATUS     current
				DESCRIPTION
					"The associated request times."
				::= { dot11WlanStatsEntry  2 }
wlanAssocRespTimes		OBJECT-TYPE
				SYNTAX  Counter32
				MAX-ACCESS read-only
				STATUS     current
				DESCRIPTION
					"The AP responsed station request associated Times."
				::= { dot11WlanStatsEntry  3 }	
wlanAssocSuccessTimes		OBJECT-TYPE
				SYNTAX  Counter32
				MAX-ACCESS read-only
				STATUS     current
				DESCRIPTION
					"The AP responsed station request associated Times."
				::= { dot11WlanStatsEntry  4 }

wlanAssocFailTimes		OBJECT-TYPE
				SYNTAX  Counter32
				MAX-ACCESS read-only
				STATUS     current
				DESCRIPTION
					"The AP responsed station request associated Times."
				::= { dot11WlanStatsEntry  5 }
				
wlanUnassocNormallyTimes	OBJECT-TYPE
				SYNTAX  Counter32
				MAX-ACCESS read-only
				STATUS     current
				DESCRIPTION
					"The AP responsed station request unassociated Times."
				::= { dot11WlanStatsEntry  6 }
					
wlanUnassocAnomalyTimes		OBJECT-TYPE
				SYNTAX  Counter32
				MAX-ACCESS read-only
				STATUS     current
				DESCRIPTION
					"The AP no responsed station request unassociated Times."
				::= { dot11WlanStatsEntry  7 }				

--********************************************************************************
dot11WlanDataTable OBJECT-TYPE
	    SYNTAX      SEQUENCE OF Dot11WlanDataEntry
	    MAX-ACCESS  not-accessible
	    STATUS      current
	    DESCRIPTION
	        "Wlan statistics."
	    ::= { dot11wlanConfig 5 }

dot11WlanDataEntry  OBJECT-TYPE
    SYNTAX      Dot11WlanDataEntry
    MAX-ACCESS  not-accessible
    STATUS      current
    DESCRIPTION
        "Wlan statistics."
    INDEX { wlanID }
    ::= { dot11WlanDataTable 1 }
   
Dot11WlanDataEntry ::=SEQUENCE{
		SSIDAllTxDataPkts				Counter32,
		SSIDAllRxDataPkts				Counter32,
		SSIDAllTxDataBytes				Counter64,
		SSIDAllRxDataBytes				Counter64,
		SSIDAllTxAssocFrameNum				Counter32,
		SSIDAllRxAssocFrameNum				Counter32,
		SSIDALLTxDataFrameBytes				Counter64
}
SSIDAllTxDataPkts			OBJECT-TYPE
				SYNTAX  Counter32
				MAX-ACCESS read-only
				STATUS     current
				DESCRIPTION
					"The total number of send data packets."
				::= { dot11WlanDataEntry 1 }

SSIDAllRxDataPkts			OBJECT-TYPE
				SYNTAX  Counter32
				MAX-ACCESS read-only
				STATUS     current
				DESCRIPTION
					"The total number of receive data packets."
				::= { dot11WlanDataEntry 2 }

SSIDAllTxDataBytes			OBJECT-TYPE
				SYNTAX  Counter64
				MAX-ACCESS read-only
				STATUS     current
				DESCRIPTION
					"The total bytes of send data packets."
				::= { dot11WlanDataEntry 3 }

SSIDAllRxDataBytes			OBJECT-TYPE
				SYNTAX  Counter64
				MAX-ACCESS read-only
				STATUS     current
				DESCRIPTION
					"The total bytes of receive data packets."
				::= { dot11WlanDataEntry 4 }

SSIDAllTxAssocFrameNum		OBJECT-TYPE
				SYNTAX  Counter32
				MAX-ACCESS read-only
				STATUS     current
				DESCRIPTION
					"The total number of associated frame send."
				::= { dot11WlanDataEntry 5 }

SSIDAllRxAssocFrameNum		OBJECT-TYPE
				SYNTAX  Counter32
				MAX-ACCESS read-only
				STATUS     current
				DESCRIPTION
					"The total number of associated frame receive."
				::= { dot11WlanDataEntry 6 }

SSIDALLTxDataFrameBytes		OBJECT-TYPE
				SYNTAX  Counter64
				MAX-ACCESS read-only
				STATUS     current
				DESCRIPTION
					"The total number of transmit data frame bytes."
				::= { dot11WlanDataEntry 7 }
dot11SSIDConfigTable OBJECT-TYPE
	    SYNTAX      SEQUENCE OF Dot11SSIDConfigEntry
	    MAX-ACCESS  not-accessible
	    STATUS      current
	    DESCRIPTION
	        "This table shows SSID stats information."
	    ::= { dot11wlanConfig 6 }
dot11SSIDConfigEntry  OBJECT-TYPE
    SYNTAX      Dot11SSIDConfigEntry
    MAX-ACCESS  not-accessible
    STATUS      current
    DESCRIPTION
        "SSID Config information."
    INDEX { wlanID		}
    ::= { dot11SSIDConfigTable 1 }
   
Dot11SSIDConfigEntry ::=SEQUENCE{
		NewSSIDName			DisplayString,
		NewSSIDEnabled 			INTEGER,
		NewSSIDHidden			INTEGER,
                NewStaIsolate                   INTEGER,
                NewDot11Auth                    INTEGER,
                Newsecurity                     INTEGER,
                NewAuthenMode                   INTEGER,
                NewSecurityCiphers              INTEGER,
                NewEncrInputType		INTEGER,
                NewSecurityKEY			DisplayString,
                NewExtensibleAuth		INTEGER,
                NewAuthIP			IpAddress,
                NewAuthPort			INTEGER,
                NewAuthSharedSecret		DisplayString,
                NewAcctIP			IpAddress,
                NewAcctPort			INTEGER,
                NewAcctSharedSecret		DisplayString,
                NewVlanId                       INTEGER,
                NewMaxSimultUsers               Integer32,
                NewStaUplinkMaxRate             Integer32,
                NewStaDwlinkMaxRate             Integer32,
                SSIDRowStatus                   RowStatus,
                StasDeadTime			TimeTicks,
                AuthDeadTime			TimeTicks,
		NewWapiAuthIP			IpAddress,
                NewWapiCertificationType	INTEGER,
                NewWapiASCertificationPath	DisplayString,
		NewWapiAECertificationPath	DisplayString
}
NewSSIDName			OBJECT-TYPE
				SYNTAX  DisplayString
				MAX-ACCESS read-create
				STATUS     current
				DESCRIPTION
					"Create SSName."
				::= { dot11SSIDConfigEntry 1 }
NewSSIDEnabled		        OBJECT-TYPE
				SYNTAX  INTEGER{
					no(0),
					yes(1)					
					}
				MAX-ACCESS read-write
				STATUS     current
				DESCRIPTION
					"NewSSIDEnabled ."
				::= { dot11SSIDConfigEntry 2 }
NewSSIDHidden			OBJECT-TYPE
				SYNTAX  INTEGER{
					no(0),
					yes(1)					
					}
				MAX-ACCESS read-write
				STATUS     current
				DESCRIPTION
					"NewSSIDHidden ."
				::= { dot11SSIDConfigEntry 3 }
NewStaIsolate			OBJECT-TYPE
				SYNTAX  INTEGER{
					no(0),
					yes(1)					
					}
				MAX-ACCESS read-write
				STATUS     current
				DESCRIPTION
					"NewStaIsolate ."
				::= { dot11SSIDConfigEntry 4 }
NewDot11Auth			OBJECT-TYPE
				SYNTAX  INTEGER{
					open(1),
					shared(2)					
					}
				MAX-ACCESS read-create
				STATUS     current
				DESCRIPTION
					"NewDot11Auth ."
				::= { dot11SSIDConfigEntry 5 }
Newsecurity			OBJECT-TYPE
				SYNTAX  INTEGER{
					none(1),
					wpa(2),
					wpa2(3),
					wapi(4)
					}
				MAX-ACCESS read-create
				STATUS     current
				DESCRIPTION
					"Newsecurity ."
				::= { dot11SSIDConfigEntry 6 }
NewAuthenMode			OBJECT-TYPE
				SYNTAX  INTEGER{
					none(1),
					PSK(2),
					Radius(3),
					wpai-cer(4)
					}
				MAX-ACCESS read-create
				STATUS     current
				DESCRIPTION
					"NewAuthenMode ."
				::= { dot11SSIDConfigEntry 7 }
NewSecurityCiphers		OBJECT-TYPE
				SYNTAX  INTEGER{
					none(1),
					wep40(2),
                                        wep104(3),
					aes(4),
					tkip(5),
					sms4(6)
					}
				MAX-ACCESS read-create
				STATUS     current
				DESCRIPTION
					"NewSecurityCiphers ."
				::= { dot11SSIDConfigEntry 8 }
				
NewEncrInputType		OBJECT-TYPE
				SYNTAX  INTEGER{
					NONE(0),
					ASCII(1),
					HEX(2)
					}
				MAX-ACCESS read-create
				STATUS     current
				DESCRIPTION
					"Input type key.While security type is none,this value cannot be set."
				::= { dot11SSIDConfigEntry 9 }		

NewSecurityKEY			OBJECT-TYPE
				SYNTAX  DisplayString
				MAX-ACCESS read-create
				STATUS     current
				DESCRIPTION
					"Key.While security type is none,this value cannot be set."
				::= { dot11SSIDConfigEntry 10 }

NewExtensibleAuth		OBJECT-TYPE
				SYNTAX  INTEGER{
						disable(0),
						enable(1)
						}
				MAX-ACCESS read-write
				STATUS     current
				DESCRIPTION
					"Extensible authentication.This value is just for open and shared security type."
				::= { dot11SSIDConfigEntry 11 }
				
NewAuthIP			OBJECT-TYPE
				SYNTAX  IpAddress
				MAX-ACCESS read-create
				STATUS     current
				DESCRIPTION
					"Security Auth IP."
				::= { dot11SSIDConfigEntry 12 }			

NewAuthPort			OBJECT-TYPE
				SYNTAX  INTEGER
				MAX-ACCESS read-create
				STATUS     current
				DESCRIPTION
					"Security Auth Port."
				::= { dot11SSIDConfigEntry 13 }

NewAuthSharedSecret		OBJECT-TYPE
				SYNTAX  DisplayString
				MAX-ACCESS read-create
				STATUS     current
				DESCRIPTION
					"Security Auth Shared Secret."
				::= { dot11SSIDConfigEntry 14 }
				
NewAcctIP			OBJECT-TYPE
				SYNTAX  IpAddress
				MAX-ACCESS read-create
				STATUS     current
				DESCRIPTION
					"Security Acct IP."
				::= { dot11SSIDConfigEntry 15 }
				
NewAcctPort			OBJECT-TYPE
				SYNTAX  INTEGER
				MAX-ACCESS read-create
				STATUS     current
				DESCRIPTION
					"Security Acct Port."
				::= { dot11SSIDConfigEntry 16 }

NewAcctSharedSecret		OBJECT-TYPE
				SYNTAX  DisplayString
				MAX-ACCESS read-create
				STATUS     current
				DESCRIPTION
					"Security Acct Shared Secret."
				::= { dot11SSIDConfigEntry 17 }						
				
NewVlanId			OBJECT-TYPE
				SYNTAX  INTEGER
				MAX-ACCESS read-write
				STATUS     current
				DESCRIPTION
					"NewVlanId ."
				::= { dot11SSIDConfigEntry 18 }
NewMaxSimultUsers	        OBJECT-TYPE
				SYNTAX  Integer32
				MAX-ACCESS read-write
				STATUS     current
				DESCRIPTION
					"NewMaxSimultUsers ."
				::= { dot11SSIDConfigEntry 19 }
NewStaUplinkMaxRate	        OBJECT-TYPE
				SYNTAX  Integer32
				MAX-ACCESS read-write
				STATUS     current
				DESCRIPTION
					"NewStaUplinkMaxRate. 0 meaning not limited to speed"
				::= { dot11SSIDConfigEntry 20 }
NewStaDwlinkMaxRate	        OBJECT-TYPE
				SYNTAX  Integer32
				MAX-ACCESS read-write
				STATUS     current
				DESCRIPTION
					"NewStaDwlinkMaxRate .0 meaning not limited to speed"
				::= { dot11SSIDConfigEntry 21 }
SSIDRowStatus	                OBJECT-TYPE
		    	        SYNTAX      RowStatus
		    	        MAX-ACCESS  read-create
		    	        STATUS      current
		         	DESCRIPTION
		        	"This variable is used to create, modify, and/or delete a row
		        	 in this table."
		    	        ::= { dot11SSIDConfigEntry 22 }
StasDeadTime	        	OBJECT-TYPE
				SYNTAX  TimeTicks
				MAX-ACCESS read-write
				STATUS     current
				DESCRIPTION
					"The station dead time,the value must multiple of 15."
				::= { dot11SSIDConfigEntry 25 }
AuthDeadTime	        	OBJECT-TYPE
				SYNTAX  TimeTicks
				MAX-ACCESS read-write
				STATUS     current
				DESCRIPTION
					"The auth user dead time"
				::= { dot11SSIDConfigEntry 26 }
NewWapiAuthIP			OBJECT-TYPE
				SYNTAX  IpAddress
				MAX-ACCESS read-create
				STATUS     current
				DESCRIPTION
					"Wapi Auth IP,this value is just for wapi_auth security mode."
				::= { dot11SSIDConfigEntry 27 }
				
NewWapiCertificationType	OBJECT-TYPE
				SYNTAX  INTEGER{
						X509(1),
						GBW(2)
						}
				MAX-ACCESS read-create
				STATUS     current
				DESCRIPTION
					"Wapi certification type,this value is just for wapi_auth security mode."
				::= { dot11SSIDConfigEntry 28 }
				
NewWapiASCertificationPath	OBJECT-TYPE
				SYNTAX  DisplayString
				MAX-ACCESS read-create
				STATUS     current
				DESCRIPTION
					"Wapi AS certification path,this value is just for wapi_auth security mode."
				::= { dot11SSIDConfigEntry 29 }		
				
NewWapiAECertificationPath	OBJECT-TYPE
				SYNTAX  DisplayString
				MAX-ACCESS read-create
				STATUS     current
				DESCRIPTION
					"Wapi AS certification path,this value is just for wapi_auth security mode."
				::= { dot11SSIDConfigEntry 30 }												


dot11CreateSecurityTable OBJECT-TYPE
	    SYNTAX      SEQUENCE OF Dot11CreateSecurityEntry
	    MAX-ACCESS  not-accessible
	    STATUS      current
	    DESCRIPTION
	        "This table create wlan."
	    ::= { dot11securityConfig 1 }

dot11CreateSecurityEntry  OBJECT-TYPE
    SYNTAX      Dot11CreateSecurityEntry
    MAX-ACCESS  not-accessible
    STATUS      current
    DESCRIPTION
        "Create wlan."
    INDEX { securityID }
    ::= { dot11CreateSecurityTable 1 }
   
Dot11CreateSecurityEntry ::=SEQUENCE{
	securityID		INTEGER,
	securityName		DisplayString,
	securityRowStatus	RowStatus
}
securityID		OBJECT-TYPE
			SYNTAX  INTEGER
			MAX-ACCESS read-create
			STATUS     current
			DESCRIPTION
				"Create security ID."
			::= { dot11CreateSecurityEntry 1 }

securityName		OBJECT-TYPE
			SYNTAX  DisplayString(SIZE(1..15))
			MAX-ACCESS read-create
			STATUS     current
			DESCRIPTION
				"Security name."
			::= { dot11CreateSecurityEntry 2 }

securityRowStatus	OBJECT-TYPE
		    	SYNTAX      RowStatus
		    	MAX-ACCESS  read-create
		    	STATUS      current
		    	DESCRIPTION
		        	"This variable is used to create, modify, and/or delete a row
		        	 in this table."
		    	::= { dot11CreateSecurityEntry 3 }
--*********************************************************************************
dot11ConfigSecurityTable OBJECT-TYPE
	    SYNTAX      SEQUENCE OF Dot11ConfigSecurityEntry
	    MAX-ACCESS  not-accessible
	    STATUS      current
	    DESCRIPTION
	        "This table Config security."
	    ::= { dot11securityConfig 2 }

dot11ConfigSecurityEntry  OBJECT-TYPE
    SYNTAX      Dot11ConfigSecurityEntry
    MAX-ACCESS  not-accessible
    STATUS      current
    DESCRIPTION
        "Config security."
    INDEX { securityID }
    ::= { dot11ConfigSecurityTable 1 }
   
Dot11ConfigSecurityEntry ::=SEQUENCE{
	securityType		INTEGER,
	encryptionType		INTEGER,
	encryptionInputTypeKey	INTEGER,
	securityKEY		DisplayString,
	extensibleAuth		INTEGER,
	authIP			DisplayString,
	authPort		INTEGER,
	authSharedSecret	DisplayString,
	acctIP			DisplayString,
	acctPort		INTEGER,
	acctSharedSecret	DisplayString,
	hostIP			DisplayString,
	radiusServer		INTEGER,
	acctInterimInterval	INTEGER,
	eapReauthPeriod		INTEGER,
	wapiASIP		DisplayString,
	wapiASType		INTEGER,
	wapiASCertificationPath		DisplayString,
	wapiIsInstalledASCer		TruthValue,
	wapiUnicastRekeyMethod		INTEGER,
	wapiMulticastRekeyMethod	INTEGER,
	wapiUnicastRekeyTime		Unsigned32,
	wapiUnicastRekeyPackets		Unsigned32,
	wapiMulticastRekeyTime		Unsigned32,
	wapiMulticastRekeyPackets	Unsigned32,
	PSKValue		DisplayString,
	PSKPassPhrase		DisplayString,
	RadiusAuthServerIPAdd		DisplayString,
	RadiusAuthServerPort		INTEGER,
	RadiusAuthServerSharedKey	DisplayString,
	RadiusAccServerIPAdd		DisplayString,
	RadiusAccServerPort		INTEGER,
	RadiusAccServerSharedKey	DisplayString,
        wapiAECertificationPath         DisplayString,
        HybridAuthSwitch		INTEGER
}
securityType		OBJECT-TYPE
			SYNTAX  INTEGER{
					open(0),
					shared(1),
					IEEE8021x(2),
					wpa-p(3),
					wpa2-p(4),
					wpa-e(5),
					wpa2-e(6),
					md5(7),
					wapi-psk(8),
					wapi-auth(9)
					}
			MAX-ACCESS read-write
			STATUS     current
			DESCRIPTION
				"Security type."
			::= { dot11ConfigSecurityEntry 1 }

encryptionType		OBJECT-TYPE
			SYNTAX  INTEGER{
					none(0),
					wep(1),
					aes(2),
					tkip(3),
					sms4(4)
					}
			MAX-ACCESS read-write
			STATUS     current
			DESCRIPTION
				"Encryption Type.
				 Different security type support different encryption type:
				 OPEN:none,WEP
				 shared:WEP
				 802.1x:WEP
				 WPA_E:AES,TKIP
				 WPA_P:AES,TKIP
				 WPA2_E:AES,TKIP
				 WPA2_P:AES,TKIP
				 WAPI_PSK:SMS4
				 WAPI_AUTH:SMS4.
				 Security type must suit for encryption type,otherwise the value will not be set."
			::= { dot11ConfigSecurityEntry 2 }

encryptionInputTypeKey	OBJECT-TYPE
			SYNTAX  INTEGER{
					ASCII(1),
					HEX(2)
					}
			MAX-ACCESS read-write
			STATUS     current
			DESCRIPTION
				"Input type key.While security type is none,this value cannot be set."
			::= { dot11ConfigSecurityEntry 3 }

securityKEY		OBJECT-TYPE
			SYNTAX  DisplayString
			MAX-ACCESS read-write
			STATUS     current
			DESCRIPTION
				"Key.While security type is none,this value cannot be set."
			::= { dot11ConfigSecurityEntry 4 }

extensibleAuth		OBJECT-TYPE
			SYNTAX  INTEGER{
					disable(0),
					enable(1)
					}
			MAX-ACCESS read-write
			STATUS     current
			DESCRIPTION
				"Extensible authentication.This value is just for open and shared security type."
			::= { dot11ConfigSecurityEntry 5 }

authIP			OBJECT-TYPE
			SYNTAX  DisplayString
			MAX-ACCESS read-write
			STATUS     current
			DESCRIPTION
				"Security Auth IP."
			::= { dot11ConfigSecurityEntry 6 }

authPort		OBJECT-TYPE
			SYNTAX  INTEGER
			MAX-ACCESS read-write
			STATUS     current
			DESCRIPTION
				"Security Auth Port."
			::= { dot11ConfigSecurityEntry 7 }

authSharedSecret	OBJECT-TYPE
			SYNTAX  DisplayString
			MAX-ACCESS read-write
			STATUS     current
			DESCRIPTION
				"Security Auth Shared Secret."
			::= { dot11ConfigSecurityEntry 8 }

acctIP			OBJECT-TYPE
			SYNTAX  DisplayString
			MAX-ACCESS read-write
			STATUS     current
			DESCRIPTION
				"Security Acct IP."
			::= { dot11ConfigSecurityEntry 9 }

acctPort		OBJECT-TYPE
			SYNTAX  INTEGER
			MAX-ACCESS read-write
			STATUS     current
			DESCRIPTION
				"Security Acct Port."
			::= { dot11ConfigSecurityEntry 10 }

acctSharedSecret	OBJECT-TYPE
			SYNTAX  DisplayString
			MAX-ACCESS read-write
			STATUS     current
			DESCRIPTION
				"Security Acct Shared Secret."
			::= { dot11ConfigSecurityEntry 11 }

hostIP			OBJECT-TYPE
			SYNTAX  DisplayString
			MAX-ACCESS read-write
			STATUS     current
			DESCRIPTION
				"Host IP."
			::= { dot11ConfigSecurityEntry 12 }

radiusServer		OBJECT-TYPE
			SYNTAX  INTEGER{
					wireless(0),
					wired(1)
					}
			MAX-ACCESS read-write
			STATUS     current
			DESCRIPTION
				"RadiusServer."
			::= { dot11ConfigSecurityEntry 13 }

acctInterimInterval	OBJECT-TYPE
			SYNTAX  INTEGER(0..32767)
			MAX-ACCESS read-write
			STATUS     current
			DESCRIPTION
				"Acct interim interval."
			::= { dot11ConfigSecurityEntry 14 }

eapReauthPeriod		OBJECT-TYPE
			SYNTAX  INTEGER(0..32767)
			MAX-ACCESS read-write
			STATUS     current
			DESCRIPTION
				"Eap Reauth Period."
			::= { dot11ConfigSecurityEntry 15 }

wapiASIP		OBJECT-TYPE
			SYNTAX  DisplayString
			MAX-ACCESS read-write
			STATUS     current
			DESCRIPTION
				"WAPI AS  IP.This value is just for wapi_auth security mode."
			::= { dot11ConfigSecurityEntry 16 }

wapiASType		OBJECT-TYPE
			SYNTAX  INTEGER{
					X509(1),
					GBW(2)
					}
			MAX-ACCESS read-write
			STATUS     current
			DESCRIPTION
				"WAPI AS type.This value is just for wapi_auth security mode."
			::= { dot11ConfigSecurityEntry 17 }

wapiASCertificationPath	OBJECT-TYPE
			SYNTAX  DisplayString
			MAX-ACCESS read-write
			STATUS     current
			DESCRIPTION
				"WAPI AS Certification Path.This value is just for wapi_auth security mode."
			::= { dot11ConfigSecurityEntry 18 }

wapiIsInstalledASCer	OBJECT-TYPE
			SYNTAX  TruthValue
			MAX-ACCESS read-only
			STATUS     current
			DESCRIPTION
				"Whether the AS certificate is installed."
			::= { dot11ConfigSecurityEntry 19 }

wapiUnicastRekeyMethod			OBJECT-TYPE
					SYNTAX     INTEGER{
							disable(0),
							time-based(1),
							packet-based(2),
							both-based(3)
							}
					MAX-ACCESS read-write
					STATUS     current
					DESCRIPTION
						"Wapi unicast rekey method."
					::= { dot11ConfigSecurityEntry 20 }

wapiMulticastRekeyMethod		OBJECT-TYPE
					SYNTAX     INTEGER{
							disable(0),
							time-based(1),
							packet-based(2),
							both-based(3)
							}
					MAX-ACCESS read-write
					STATUS     current
					DESCRIPTION
						"Wapi multicast rekey method."
					::= { dot11ConfigSecurityEntry 21 }

wapiUnicastRekeyTime			OBJECT-TYPE
					SYNTAX     Unsigned32(0..4000000000)
					MAX-ACCESS read-write
					STATUS     current
					DESCRIPTION
						"Unicast key valid time."
					::= { dot11ConfigSecurityEntry 22 }

wapiUnicastRekeyPackets			OBJECT-TYPE
					SYNTAX     Unsigned32(0..4000000000)
					MAX-ACCESS read-write
					STATUS     current
					DESCRIPTION
						"Unicast key valid data packets amount."
					::= { dot11ConfigSecurityEntry 23 }

wapiMulticastRekeyTime			OBJECT-TYPE
					SYNTAX     Unsigned32(0..4000000000)
					MAX-ACCESS read-write
					STATUS     current
					DESCRIPTION
						"Multicast key valid time."
					::= { dot11ConfigSecurityEntry 24 }

wapiMulticastRekeyPackets		OBJECT-TYPE
					SYNTAX     Unsigned32(0..4000000000)
					MAX-ACCESS read-write
					STATUS     current
					DESCRIPTION
						"Multicast key valid data packets amount."
					::= { dot11ConfigSecurityEntry 25 }
					
PSKValue				OBJECT-TYPE
					SYNTAX  DisplayString
					MAX-ACCESS read-write
					STATUS     current
					DESCRIPTION
						"PSK Value."
					::= { dot11ConfigSecurityEntry 26 }
	
PSKPassPhrase				OBJECT-TYPE
					SYNTAX  DisplayString
					MAX-ACCESS read-write
					STATUS     current
					DESCRIPTION
						"The pass-phrase which generated PSK."
					::= { dot11ConfigSecurityEntry 27 }		
	
RadiusAuthServerIPAdd			OBJECT-TYPE
					SYNTAX  DisplayString
					MAX-ACCESS read-write
					STATUS     current
					DESCRIPTION
						"Secondary Security Auth IP."
					::= { dot11ConfigSecurityEntry 28 }	
	
RadiusAuthServerPort			OBJECT-TYPE
					SYNTAX  INTEGER
					MAX-ACCESS read-write
					STATUS     current
					DESCRIPTION
						"Secondary Security Auth Port."
					::= { dot11ConfigSecurityEntry 29 }

RadiusAuthServerSharedKey		OBJECT-TYPE
					SYNTAX  DisplayString
					MAX-ACCESS read-write
					STATUS     current
					DESCRIPTION
						"Secondary Security Auth Shared Key."
					::= { dot11ConfigSecurityEntry 30 }

RadiusAccServerIPAdd			OBJECT-TYPE
					SYNTAX  DisplayString
					MAX-ACCESS read-write
					STATUS     current
					DESCRIPTION
						"Secondary Security Acct IP."
					::= { dot11ConfigSecurityEntry 31 }

RadiusAccServerPort			OBJECT-TYPE
					SYNTAX  INTEGER
					MAX-ACCESS read-write
					STATUS     current
					DESCRIPTION
						"Secondary Security Acct Port."
					::= { dot11ConfigSecurityEntry 32 }

RadiusAccServerSharedKey		OBJECT-TYPE
					SYNTAX  DisplayString
					MAX-ACCESS read-write
					STATUS     current
					DESCRIPTION
						"Secondary Security Acct Shared Key."
					::= { dot11ConfigSecurityEntry 33 }					
wapiAECertificationPath	                OBJECT-TYPE
					SYNTAX  DisplayString
					MAX-ACCESS read-write
					STATUS     current
					DESCRIPTION
						"wapiAECertificationPath."
					::= { dot11ConfigSecurityEntry 34 }	
					
HybridAuthSwitch	                OBJECT-TYPE
					SYNTAX  INTEGER{
						       enable(1),
						       disable(2)
						       }
					MAX-ACCESS read-write
					STATUS     current
					DESCRIPTION
						"Hybrid Authentication Switch."
					::= { dot11ConfigSecurityEntry 41 }														
--*********************************************************************************
dot11ConfigPskTable OBJECT-TYPE
	    SYNTAX      SEQUENCE OF Dot11ConfigPskEntry
	    MAX-ACCESS  not-accessible
	    STATUS      current
	    DESCRIPTION
	        "This table Config Psk."
	    ::= { dot11securityConfig 3 }

dot11ConfigPskEntry  OBJECT-TYPE
    SYNTAX      Dot11ConfigPskEntry
    MAX-ACCESS  not-accessible
    STATUS      current
    DESCRIPTION
        "Config Psk."
    INDEX { PskSSID   }
    ::= { dot11ConfigPskTable 1 }

Dot11ConfigPskEntry ::=SEQUENCE{
                PskSSID                            INTEGER,
		PSKCipherKeyValue		DisplayString,
		PSKCipherKeyCharType		INTEGER
}
PskSSID                          OBJECT-TYPE
				SYNTAX  INTEGER
				MAX-ACCESS read-only
				STATUS     current
				DESCRIPTION
					"WlanID."
				::= { dot11ConfigPskEntry 1 }

PSKCipherKeyValue			OBJECT-TYPE
				SYNTAX  DisplayString
				MAX-ACCESS read-write
				STATUS     current
				DESCRIPTION
					"CipherKeyValue."
				::= { dot11ConfigPskEntry 2}

PSKCipherKeyCharType			OBJECT-TYPE
				SYNTAX  INTEGER{
                                                char(1),
                                                hex(2)
                                                }
				MAX-ACCESS read-write
				STATUS     current
				DESCRIPTION
					"CipherKeyCharType."
				::= { dot11ConfigPskEntry 3 }
--*********************************************************************************
dot11ConfigWepTable OBJECT-TYPE
	    SYNTAX      SEQUENCE OF Dot11ConfigWepEntry
	    MAX-ACCESS  not-accessible
	    STATUS      current
	    DESCRIPTION
	        "This table Config Wep."
	    ::= { dot11securityConfig 4 }

dot11ConfigWepEntry  OBJECT-TYPE
    SYNTAX      Dot11ConfigWepEntry
    MAX-ACCESS  not-accessible
    STATUS      current
    DESCRIPTION
        "Config Wep."
    INDEX { WepSSID }
    ::= { dot11ConfigWepTable 1 }

Dot11ConfigWepEntry ::=SEQUENCE{
                WepSSID                          INTEGER,
		WepCipherKeyValue		DisplayString,
		WepCipherKeyCharType		INTEGER,
                WepSSIDIndex                    INTEGER
}

WepSSID			        OBJECT-TYPE
				SYNTAX  INTEGER
				MAX-ACCESS read-only
				STATUS     current
				DESCRIPTION
					"SSID."
				::= { dot11ConfigWepEntry 1}

WepCipherKeyValue			OBJECT-TYPE
				SYNTAX  DisplayString
				MAX-ACCESS read-write
				STATUS     current
				DESCRIPTION
					"CipherKeyValue."
				::= { dot11ConfigWepEntry 2}

WepCipherKeyCharType			OBJECT-TYPE
				SYNTAX  INTEGER{
                                                char(1),
                                                hex(2)
                                                }
				MAX-ACCESS read-write
				STATUS     current
				DESCRIPTION
					"CipherKeyCharType."
				::= { dot11ConfigWepEntry 3 }

WepSSIDIndex			OBJECT-TYPE
				SYNTAX  INTEGER
				MAX-ACCESS read-write
				STATUS     current
				DESCRIPTION
					"SSID wep security index."
				::= { dot11ConfigWepEntry 4}
--*********************************************************************************
dot11ConfigWapiTable OBJECT-TYPE
	    SYNTAX      SEQUENCE OF Dot11ConfigWapiEntry
	    MAX-ACCESS  not-accessible
	    STATUS      current
	    DESCRIPTION
	        "This table Config Wep."
	    ::= { dot11securityConfig 5 }

dot11ConfigWapiEntry  OBJECT-TYPE
    SYNTAX      Dot11ConfigWapiEntry
    MAX-ACCESS  not-accessible
    STATUS      current
    DESCRIPTION
        "Config Wapi."
    INDEX { WapiSSID }
    ::= { dot11ConfigWapiTable 1 }

Dot11ConfigWapiEntry ::=SEQUENCE{
                WapiSSID                  	INTEGER,
		WAPIASIPAddress			IpAddress,
		WapiIsInstalledCer		TruthValue
}

WapiSSID		OBJECT-TYPE
				SYNTAX  INTEGER
				MAX-ACCESS read-only
				STATUS     current
				DESCRIPTION
					"WAPIASIPAddress	."
				::= { dot11ConfigWapiEntry 1}

WAPIASIPAddress			OBJECT-TYPE
				SYNTAX  IpAddress
				MAX-ACCESS read-write
				STATUS     current
				DESCRIPTION
					"WAPIASIPAddress	."
				::= { dot11ConfigWapiEntry 2}

WapiIsInstalledCer		OBJECT-TYPE
				SYNTAX  TruthValue 
				MAX-ACCESS read-only
				STATUS     current
				DESCRIPTION
					"Whether installed WAPI ae certificate."
				::= { dot11ConfigWapiEntry 3}
--*********************************************************************************
dot11ConfigRadiusAuthServerTable OBJECT-TYPE
	    SYNTAX      SEQUENCE OF Dot11ConfigRadiusAuthServerEntry
	    MAX-ACCESS  not-accessible
	    STATUS      current
	    DESCRIPTION
	        "This table Config RadiusAuthServer."
	    ::= { dot11securityConfig 6 }

dot11ConfigRadiusAuthServerEntry  OBJECT-TYPE
    SYNTAX      Dot11ConfigRadiusAuthServerEntry
    MAX-ACCESS  not-accessible
    STATUS      current
    DESCRIPTION
        "Config RadiusAuthServer."
    INDEX { RadiusAuthServerID }
    ::= { dot11ConfigRadiusAuthServerTable 1 }

Dot11ConfigRadiusAuthServerEntry ::=SEQUENCE{
                RadiusAuthServerID                  INTEGER,
		NewAuthServerIPAdd	IpAddress,
		NewAuthServerPort		INTEGER,
                NewAuthServerSharedkey    DisplayString,
                NewRadiusAuthServerIPAdd            IpAddress,
                NewRadiusAuthServerPort         INTEGER,
                NewRadiusAuthServerSharedkey    DisplayString
}

RadiusAuthServerID	        OBJECT-TYPE
				SYNTAX  INTEGER
				MAX-ACCESS read-only
				STATUS     current
				DESCRIPTION
					"RadiusAuthServerID."
				::= { dot11ConfigRadiusAuthServerEntry 1 }

NewAuthServerIPAdd	        OBJECT-TYPE
				SYNTAX  IpAddress
				MAX-ACCESS read-write
				STATUS     current
				DESCRIPTION
					"NewAuthServerIPAdd."
				::= { dot11ConfigRadiusAuthServerEntry 2 }
NewAuthServerPort	        OBJECT-TYPE
				SYNTAX  INTEGER
				MAX-ACCESS read-write
				STATUS     current
				DESCRIPTION
					"NewAuthServerPort."
				::= { dot11ConfigRadiusAuthServerEntry 3 }

NewAuthServerSharedkey	        OBJECT-TYPE
				SYNTAX  DisplayString
				MAX-ACCESS read-write
				STATUS     current
				DESCRIPTION
					"NewAuthServerSharedkey."
				::= { dot11ConfigRadiusAuthServerEntry 4 }
NewRadiusAuthServerIPAdd	OBJECT-TYPE
				SYNTAX  IpAddress
				MAX-ACCESS read-write
				STATUS     current
				DESCRIPTION
					"NewRadiusAuthServerIPAdd."
				::= { dot11ConfigRadiusAuthServerEntry 5 }
NewRadiusAuthServerPort	        OBJECT-TYPE
				SYNTAX  INTEGER
				MAX-ACCESS read-write
				STATUS     current
				DESCRIPTION
					"NewRadiusAuthServerPort."
				::= { dot11ConfigRadiusAuthServerEntry 6 }
NewRadiusAuthServerSharedkey	OBJECT-TYPE
				SYNTAX  DisplayString
				MAX-ACCESS read-write
				STATUS     current
				DESCRIPTION
					"NewRadiusAuthServerSharedkey."
				::= { dot11ConfigRadiusAuthServerEntry 7 }
--*********************************************************************************
dot11ConfigRadiusAccServerTable OBJECT-TYPE
	    SYNTAX      SEQUENCE OF Dot11ConfigRadiusAccServerEntry
	    MAX-ACCESS  not-accessible
	    STATUS      current
	    DESCRIPTION
	        "This table Config RadiusAccServer."
	    ::= { dot11securityConfig 7 }

dot11ConfigRadiusAccServerEntry  OBJECT-TYPE
    SYNTAX      Dot11ConfigRadiusAccServerEntry
    MAX-ACCESS  not-accessible
    STATUS      current
    DESCRIPTION
        "Config RadiusAccServer."
    INDEX { RadiusAccServerID }
    ::= { dot11ConfigRadiusAccServerTable 1 }

Dot11ConfigRadiusAccServerEntry ::=SEQUENCE{
                RadiusAccServerID                  INTEGER,
		NewAccServerIPAdd	IpAddress,
		NewAccServerPort		INTEGER,
                NewAccServerSharedkey    DisplayString,
                NewRadiusAccServerIPAdd            IpAddress,
                NewRadiusAccServerPort         INTEGER,
                NewRadiusAccServerSharedkey    DisplayString
}

RadiusAccServerID	        OBJECT-TYPE
				SYNTAX  INTEGER
				MAX-ACCESS read-only
				STATUS     current
				DESCRIPTION
					"RadiusAccServerID."
				::= { dot11ConfigRadiusAccServerEntry 1 }

NewAccServerIPAdd	        OBJECT-TYPE
				SYNTAX  IpAddress
				MAX-ACCESS read-write
				STATUS     current
				DESCRIPTION
					"NewAccServerIPAdd."
				::= { dot11ConfigRadiusAccServerEntry 2 }
NewAccServerPort	        OBJECT-TYPE
				SYNTAX  INTEGER
				MAX-ACCESS read-write
				STATUS     current
				DESCRIPTION
					"NewAccServerPort."
				::= { dot11ConfigRadiusAccServerEntry 3 }

NewAccServerSharedkey	        OBJECT-TYPE
				SYNTAX  DisplayString
				MAX-ACCESS read-write
				STATUS     current
				DESCRIPTION
					"NewAccServerSharedkey."
				::= { dot11ConfigRadiusAccServerEntry 4 }
NewRadiusAccServerIPAdd	        OBJECT-TYPE
				SYNTAX  IpAddress
				MAX-ACCESS read-write
				STATUS     current
				DESCRIPTION
					"NewRadiusAccServerIPAdd."
				::= { dot11ConfigRadiusAccServerEntry 5 }
NewRadiusAccServerPort	        OBJECT-TYPE
				SYNTAX  INTEGER
				MAX-ACCESS read-write
				STATUS     current
				DESCRIPTION
					"NewRadiusAccServerPort."
				::= { dot11ConfigRadiusAccServerEntry 6 }
NewRadiusAccServerSharedkey	OBJECT-TYPE
				SYNTAX  DisplayString
				MAX-ACCESS read-write
				STATUS     current
				DESCRIPTION
					"NewRadiusAccServerSharedkey."
				::= { dot11ConfigRadiusAccServerEntry 7 }
--*********************************************************************************

--*********************************************************************************
dot11AcVersionAndConfig OBJECT IDENTIFIER ::={ dot11AcGroup 15 }

dot11AcVersionAndConfigTable OBJECT-TYPE
	    SYNTAX      SEQUENCE OF Dot11AcVersionAndConfigEntry
	    MAX-ACCESS  not-accessible
	    STATUS      current
	    DESCRIPTION
	        "Shows version and config."
	    ::= { dot11AcVersionAndConfig 1 }

dot11AcVersionAndConfigEntry  OBJECT-TYPE
    SYNTAX      Dot11AcVersionAndConfigEntry
    MAX-ACCESS  not-accessible
    STATUS      current
    DESCRIPTION
        "Shows version and config."
    INDEX { LoadFlag }
    ::= { dot11AcVersionAndConfigTable 1 }
   
Dot11AcVersionAndConfigEntry ::=SEQUENCE{
		LoadFlag		INTEGER,
		FileName		DisplayString,
		FileType		INTEGER,
		EstimateFileSize	INTEGER,
		TransProtocol		INTEGER,
		ServerAddr		DisplayString,
		ServerPort		DisplayString,
		ServerUsername		DisplayString,
		ServerPasswd		DisplayString,
		TransStatus		INTEGER,
		TotalBytes		INTEGER,
		TransferBytes		INTEGER,
		FailReason		DisplayString
}
LoadFlag			OBJECT-TYPE
				SYNTAX  INTEGER{
						download(1),
						upload(2)
							}
				MAX-ACCESS read-only
				STATUS     current
				DESCRIPTION
					"Transmission type(Include download and upload)."
				::= { dot11AcVersionAndConfigEntry 1 }

FileName			OBJECT-TYPE
				SYNTAX  DisplayString
				MAX-ACCESS read-write
				STATUS     current
				DESCRIPTION
					"File name."
				::= { dot11AcVersionAndConfigEntry 2 }

FileType			OBJECT-TYPE
				SYNTAX  INTEGER{
						no(0),
						SoftVersionFile(1),
						ConfigFile(2),
						LogFile(3)
						}
				MAX-ACCESS read-write
				STATUS     current
				DESCRIPTION
					"File type(Include Software version file,config file,logo file)."
				::= { dot11AcVersionAndConfigEntry 3 }

EstimateFileSize		OBJECT-TYPE
				SYNTAX  INTEGER
				MAX-ACCESS read-write
				STATUS     current
				DESCRIPTION
					"Estimate file size(This value is used for estimate whether the device has enough space to download this file.This value only useful for down process)."
				::= { dot11AcVersionAndConfigEntry 4 }

TransProtocol			OBJECT-TYPE
				SYNTAX  INTEGER{
						NO(0),
						FTP(1),
						HTTP(2)
						}
				MAX-ACCESS read-write
				STATUS     current
				DESCRIPTION
					"Transmit protocol."
				::= { dot11AcVersionAndConfigEntry 5 }


ServerAddr			OBJECT-TYPE
				SYNTAX  DisplayString
				MAX-ACCESS read-write
				STATUS     current
				DESCRIPTION
					"Remote server address."
				::= { dot11AcVersionAndConfigEntry 6 }

ServerPort			OBJECT-TYPE
				SYNTAX  DisplayString
				MAX-ACCESS read-write
				STATUS     current
				DESCRIPTION
					"Remote server port."
				::= { dot11AcVersionAndConfigEntry 7 }


ServerUsername			OBJECT-TYPE
				SYNTAX  DisplayString
				MAX-ACCESS read-write
				STATUS     current
				DESCRIPTION
					"Remote server user name."
				::= { dot11AcVersionAndConfigEntry 8 }

ServerPasswd		OBJECT-TYPE
				SYNTAX  DisplayString
				MAX-ACCESS read-write
				STATUS     current
				DESCRIPTION
					"Remote server user password."
				::= { dot11AcVersionAndConfigEntry 9 }

TransStatus			OBJECT-TYPE
				SYNTAX  INTEGER{
						no(0),
						idle(1),
						preparing(2),
						transferring(3),
						installing(4),
						completedSucessfully(5),
						failed(6),
						aborted(7)
							}
				MAX-ACCESS read-only
				STATUS     current
				DESCRIPTION
					"Transmit status."
				::= { dot11AcVersionAndConfigEntry 10 }

TotalBytes			OBJECT-TYPE
				SYNTAX  INTEGER
				MAX-ACCESS read-write
				STATUS     current
				DESCRIPTION
					"Actual document size."
				::= { dot11AcVersionAndConfigEntry 11 }

TransferBytes			OBJECT-TYPE
				SYNTAX  INTEGER
				MAX-ACCESS read-only
				STATUS     current
				DESCRIPTION
					"The size that has been already transmited."
				::= { dot11AcVersionAndConfigEntry 12 }

FailReason			OBJECT-TYPE
				SYNTAX  DisplayString
				MAX-ACCESS read-write
				STATUS     current
				DESCRIPTION
					"Failed reason."
				::= { dot11AcVersionAndConfigEntry 13 }
				

-- **********************************************************************
-- * dot11VersionFile
-- **********************************************************************

dot11VersionFile		OBJECT IDENTIFIER ::={ dot11AcVersionAndConfig 2}
				
VFServerAddr			OBJECT-TYPE
				SYNTAX  DisplayString
				MAX-ACCESS read-write
				STATUS     current
				DESCRIPTION
					"Remote server address."
				::= { dot11VersionFile 1 }

VFServerUsername		OBJECT-TYPE
				SYNTAX  DisplayString
				MAX-ACCESS read-write
				STATUS     current
				DESCRIPTION
					"Remote server user name."
				::= { dot11VersionFile 2 }

VFServerPasswd			OBJECT-TYPE
				SYNTAX  DisplayString
				MAX-ACCESS read-write
				STATUS     current
				DESCRIPTION
					"Remote server user password."
				::= { dot11VersionFile 3 }				

VFTransferType			OBJECT-TYPE
				SYNTAX  INTEGER{
						download(1),
						upload(2)
						}
				MAX-ACCESS read-write
				STATUS     current
				DESCRIPTION
					"Transmission type(Include download and upload)."
				::= { dot11VersionFile 4 }				
				
				
-- **********************************************************************
-- * dot11ConfigurationFile
-- **********************************************************************

dot11ConfigurationFile		OBJECT IDENTIFIER ::={ dot11AcVersionAndConfig 3}
				
CFServerAddr			OBJECT-TYPE
				SYNTAX  DisplayString
				MAX-ACCESS read-write
				STATUS     current
				DESCRIPTION
					"Remote server address."
				::= { dot11ConfigurationFile 1 }

CFServerUsername		OBJECT-TYPE
				SYNTAX  DisplayString
				MAX-ACCESS read-write
				STATUS     current
				DESCRIPTION
					"Remote server user name."
				::= { dot11ConfigurationFile 2 }
				
CFServerPasswd			OBJECT-TYPE
				SYNTAX  DisplayString
				MAX-ACCESS read-write
				STATUS     current
				DESCRIPTION
					"Remote server user password."
				::= { dot11ConfigurationFile 3 }				

CFTransferType			OBJECT-TYPE
				SYNTAX  INTEGER{
						download(1),
						upload(2)
						}
				MAX-ACCESS read-write
				STATUS     current
				DESCRIPTION
					"Transmission type(Include download and upload)."
				::= { dot11ConfigurationFile 4 }				
				

-- **********************************************************************
-- * dot11AcVersionFile
-- **********************************************************************

dot11AcVersionFile		OBJECT IDENTIFIER ::={ dot11AcVersionAndConfig 4}
				
AcVfLoadFlag 			OBJECT-TYPE
				SYNTAX  INTEGER{
                                               download(1),
                                               upload(2)
                                               }
				MAX-ACCESS read-write
				STATUS     current
				DESCRIPTION
					"AcVfLoadFlag."
				::= { dot11AcVersionFile 1 }

AcVfFileName		        OBJECT-TYPE
				SYNTAX  DisplayString
				MAX-ACCESS read-write
				STATUS     current
				DESCRIPTION
					"AcVfFileName."
				::= { dot11AcVersionFile 2 }
				
AcVfTransProtocol 		OBJECT-TYPE
				SYNTAX  INTEGER
				MAX-ACCESS read-write
				STATUS     current
				DESCRIPTION
					"AcVfTransProtocol ."
				::= { dot11AcVersionFile 3 }				

AcVfServerAddr			OBJECT-TYPE
				SYNTAX  IpAddress
				MAX-ACCESS read-write
				STATUS     current
				DESCRIPTION
					"AcVfServerAddr."
				::= { dot11AcVersionFile 4 }

AcVfServerPort			OBJECT-TYPE
				SYNTAX  INTEGER
				MAX-ACCESS read-write
				STATUS     current
				DESCRIPTION
					"AcVfServerPort."
				::= { dot11AcVersionFile 5 }

AcVfServerUsername 		OBJECT-TYPE
				SYNTAX  DisplayString
				MAX-ACCESS read-write
				STATUS     current
				DESCRIPTION
					"AcVfServerUsername ."
				::= { dot11AcVersionFile 6 }

AcVfServerPasswd		OBJECT-TYPE
				SYNTAX  DisplayString
				MAX-ACCESS read-write
				STATUS     current
				DESCRIPTION
					"AcVfServerPasswd	."
				::= { dot11AcVersionFile 7 }

AcVfTransStatus			OBJECT-TYPE
				SYNTAX  INTEGER{
					 transferring(1), 
					 completedSucessfully(2), 
					 failed(3)
						}
				MAX-ACCESS read-only
				STATUS     current
				DESCRIPTION
					"AVCfTransStatus."
				::= { dot11AcVersionFile 8 }

AcVfFailReason 			OBJECT-TYPE
				SYNTAX  DisplayString
				MAX-ACCESS read-only
				STATUS     current
				DESCRIPTION
					"AcVfFailReason."
				::= { dot11AcVersionFile 9 }

-- **********************************************************************
-- * dot11AcConfigurationFile
-- **********************************************************************

dot11AcConfigurationFile		OBJECT IDENTIFIER ::={ dot11AcVersionAndConfig 5}
				
AcCfLoadFlag 			OBJECT-TYPE
				SYNTAX  INTEGER{
                                               download(1),
                                               upload(2)
                                               }
				MAX-ACCESS read-write
				STATUS     current
				DESCRIPTION
					"AcCfLoadFlag."
				::= { dot11AcConfigurationFile 1 }

AcCfFileName		        OBJECT-TYPE
				SYNTAX  DisplayString
				MAX-ACCESS read-write
				STATUS     current
				DESCRIPTION
					"AcCfFileName."
				::= { dot11AcConfigurationFile 2 }
				
AcCfTransProtocol 			        OBJECT-TYPE
				SYNTAX  INTEGER{
						ftp(2)
					       }
				MAX-ACCESS read-write
				STATUS     current
				DESCRIPTION
					"AcCfTransProtocol ."
				::= { dot11AcConfigurationFile 3 }				

AcCfServerAddr			OBJECT-TYPE
				SYNTAX  IpAddress
				MAX-ACCESS read-write
				STATUS     current
				DESCRIPTION
					"AcCfServerAddr."
				::= { dot11AcConfigurationFile 4 }

AcCfServerPort			OBJECT-TYPE
				SYNTAX  INTEGER
				MAX-ACCESS read-write
				STATUS     current
				DESCRIPTION
					"AcCfServerPort."
				::= { dot11AcConfigurationFile 5 }

AcCfServerUsername 	        OBJECT-TYPE
				SYNTAX  DisplayString
				MAX-ACCESS read-write
				STATUS     current
				DESCRIPTION
					"AcCfServerUsername ."
				::= { dot11AcConfigurationFile 6 }

AcCfServerPasswd	        OBJECT-TYPE
				SYNTAX  DisplayString
				MAX-ACCESS read-write
				STATUS     current
				DESCRIPTION
					"AcCfServerPasswd	."
				::= { dot11AcConfigurationFile 7 }

AcCfTransStatus			OBJECT-TYPE
				SYNTAX  INTEGER{
					transferring(1), 
					completedSucessfully(2), 
					failed(3)
						}
				MAX-ACCESS read-only
				STATUS     current
				DESCRIPTION
					"AcCfTransStatus."
				::= { dot11AcConfigurationFile 8 }

AcCfFailReason 			OBJECT-TYPE
				SYNTAX  DisplayString
				MAX-ACCESS read-only
				STATUS     current
				DESCRIPTION
					"AcCfFailReason."
				::= { dot11AcConfigurationFile 9 }
				
				
-- **********************************************************************
-- * dot11WtpVersionFileGroupUpdate
-- **********************************************************************
dot11WtpVersionFileGroupUpdate		OBJECT IDENTIFIER ::={ dot11AcVersionAndConfig 6}
wtpGroupUpdateID		OBJECT-TYPE
				SYNTAX  DisplayString
				MAX-ACCESS read-write
				STATUS     current
				DESCRIPTION
					"The wtp id of group update, like: 1-100"
				::= { dot11WtpVersionFileGroupUpdate 1 }
wtpVersionFileName		OBJECT-TYPE
				SYNTAX  DisplayString
				MAX-ACCESS read-write
				STATUS     current
				DESCRIPTION
					"AP version file name."
				::= { dot11WtpVersionFileGroupUpdate 2 }				
				
dot11SpeedLimit	OBJECT IDENTIFIER ::={ dot11AcGroup 16 }

dot11SpeedLimitTable OBJECT-TYPE
	    SYNTAX      SEQUENCE OF Dot11SpeedLimitEntry
	    MAX-ACCESS  not-accessible
	    STATUS      current
	    DESCRIPTION
	        "Speed limit."
	    ::= { dot11SpeedLimit 1 }

dot11SpeedLimitEntry  OBJECT-TYPE
    SYNTAX      Dot11SpeedLimitEntry
    MAX-ACCESS  not-accessible
    STATUS      current
    DESCRIPTION
        "Speed limit."
    INDEX { index }
    ::= { dot11SpeedLimitTable 1 }
   
Dot11SpeedLimitEntry ::=SEQUENCE{
		index			INTEGER,
		ipAddress		DisplayString,
		upInterface		DisplayString,
		downInterface		DisplayString,
		upBandWidth		DisplayString,
		downBandWidth		DisplayString,
		actionStatus		INTEGER,
		rowStatus		RowStatus
}
index				OBJECT-TYPE
				SYNTAX  INTEGER
				MAX-ACCESS read-create
				STATUS     current
				DESCRIPTION
					"index."
				::= { dot11SpeedLimitEntry 1 }

ipAddress			OBJECT-TYPE
				SYNTAX  DisplayString
				MAX-ACCESS read-create
				STATUS     current
				DESCRIPTION
					"Ip Address."
				::= { dot11SpeedLimitEntry 2 }

upInterface			OBJECT-TYPE
				SYNTAX  DisplayString
				MAX-ACCESS read-create
				STATUS     current
				DESCRIPTION
					"UP interface."
				::= { dot11SpeedLimitEntry 3 }

downInterface			OBJECT-TYPE
				SYNTAX  DisplayString
				MAX-ACCESS read-create
				STATUS     current
				DESCRIPTION
					"Down interface."
				::= { dot11SpeedLimitEntry 4 }

upBandWidth			OBJECT-TYPE
				SYNTAX  DisplayString
				MAX-ACCESS read-create
				STATUS     current
				DESCRIPTION
					"Up band width(Units kbyte)."
				::= { dot11SpeedLimitEntry 5 }

downBandWidth			OBJECT-TYPE
				SYNTAX  DisplayString
				MAX-ACCESS read-create
				STATUS     current
				DESCRIPTION
					"Down band width(Units kbyte)."
				::= { dot11SpeedLimitEntry 6 }

actionStatus			OBJECT-TYPE
				SYNTAX  INTEGER{
						use(1),
						unuse(2)
						}
				MAX-ACCESS read-create
				STATUS     current
				DESCRIPTION
					"Whether use this action."
				::= { dot11SpeedLimitEntry 7 }

rowStatus			OBJECT-TYPE
				SYNTAX  RowStatus
				MAX-ACCESS read-create
				STATUS     current
				DESCRIPTION
					"This variable is used to create, modify, and/or delete a row
		        	 	in this table."
				::= { dot11SpeedLimitEntry 8 }

speedAction			OBJECT-TYPE
				SYNTAX  INTEGER{
						enable(1)
						}
				MAX-ACCESS read-write
				STATUS     current
				DESCRIPTION
					"Use speed limit policy."
				::= { dot11SpeedLimit 2 }

dot11Stationinfo	OBJECT IDENTIFIER ::={ dot11AcGroup 17}

dot11StationinfoTable OBJECT-TYPE
	    SYNTAX      SEQUENCE OF Dot11StationinfoEntry
	    MAX-ACCESS  not-accessible
	    STATUS      current
	    DESCRIPTION
	        "Station Online."
	    ::= { dot11Stationinfo 1 }

dot11StationinfoEntry  OBJECT-TYPE
    SYNTAX      Dot11StationinfoEntry
    MAX-ACCESS  not-accessible
    STATUS      current
    DESCRIPTION
        "Station Online."
    INDEX { StationMac }
    ::= { dot11StationinfoTable 1 }
   
Dot11StationinfoEntry ::=SEQUENCE{
		StationMac		DisplayString,
		StationOnline		INTEGER
                                 }

StationMac				OBJECT-TYPE
				SYNTAX  DisplayString
				MAX-ACCESS read-only
				STATUS     current
				DESCRIPTION
					"Index Of StationMac."
				::= { dot11StationinfoEntry 1 }

StationOnline				OBJECT-TYPE
				SYNTAX  INTEGER{
                                                online(1),
                                                offline(2)
                                               }
				MAX-ACCESS read-only
				STATUS     current
				DESCRIPTION
					"StationOnline."
				::= { dot11StationinfoEntry 2 }   
				
InformationInfo	     OBJECT-TYPE
				SYNTAX     DisplayString
				MAX-ACCESS read-write
				STATUS     current
				DESCRIPTION
					"InformationInterface "
				::= { dot11Stationinfo 2}


dot11DHCP OBJECT IDENTIFIER ::={ dot11Service 3 }

DHCPIPPoolUsage			OBJECT-TYPE
				SYNTAX  INTEGER
				MAX-ACCESS read-only
				STATUS     current
				DESCRIPTION
					"DHCP address pool use rate."
				::= { dot11DHCP 1 }

DHCPReqTimes			OBJECT-TYPE
				SYNTAX  Counter32
				MAX-ACCESS read-only
				STATUS     current
				DESCRIPTION
					"DHCP request times."
				::= { dot11DHCP 2 }

DHCPReqSucTimes			OBJECT-TYPE
				SYNTAX  Counter32
				MAX-ACCESS read-only
				STATUS     current
				DESCRIPTION
					"DHCP request successful times."
				::= { dot11DHCP 3 }

DHCPAvgUsage			OBJECT-TYPE
				SYNTAX  INTEGER
				MAX-ACCESS read-only
				STATUS     current
				DESCRIPTION
					"DHCP raverage userate."
				::= { dot11DHCP 4 }

DHCPPeakUsage			OBJECT-TYPE
				SYNTAX  INTEGER
				MAX-ACCESS read-only
				STATUS     current
				DESCRIPTION
					"DHCP peak userate."
				::= { dot11DHCP 5 }
	
DHCPIpNum			OBJECT-TYPE
				SYNTAX  INTEGER
				MAX-ACCESS read-only
				STATUS     current
				DESCRIPTION
					"DHCP IP whole  numbers."
				::= { dot11DHCP 6 }
				
DHCPDiscoverTimes		OBJECT-TYPE
				SYNTAX  Counter32
				MAX-ACCESS read-only
				STATUS     current
				DESCRIPTION
					"DHCP discover  times."
				::= { dot11DHCP 7 }

DHCPOfferTimes			OBJECT-TYPE
				SYNTAX  Counter32
				MAX-ACCESS read-only
				STATUS     current
				DESCRIPTION
					"DHCP offer times."
				::= { dot11DHCP 8 }
				

Ipv6DHCPReqTimes			OBJECT-TYPE
				SYNTAX  Counter32
				MAX-ACCESS read-only
				STATUS     current
				DESCRIPTION
					"Ipv6 DHCP request times."
				::= { dot11DHCP 9 }

Ipv6DHCPReqSucTimes			OBJECT-TYPE
				SYNTAX  Counter32
				MAX-ACCESS read-only
				STATUS     current
				DESCRIPTION
					"Ipv6 DHCP request successful times."
				::= { dot11DHCP 10 }


				
				
				

-- **********************************************************************
-- * dot11DHCPIpAddressPoolTable
-- **********************************************************************			
				
dot11DHCPIpAddressPoolTable	OBJECT-TYPE
			    	SYNTAX      SEQUENCE OF Dot11DHCPIpAddressPoolEntry
			    	MAX-ACCESS  not-accessible
			    	STATUS      current
			    	DESCRIPTION
			        	"This table shows DHCP IP Address Pool information."
			    	::= { dot11Service 4 }		
			    	
dot11DHCPIpAddressPoolEntry  	OBJECT-TYPE
			    	SYNTAX      Dot11DHCPIpAddressPoolEntry
			    	MAX-ACCESS  not-accessible
			    	STATUS      current
			    	DESCRIPTION
			        	"DHCP IP Address Pool information."
			    	INDEX { AddPoolIndex }
			    	::= { dot11DHCPIpAddressPoolTable 1 }
			   
Dot11DHCPIpAddressPoolEntry	::=SEQUENCE{
	AddPoolIndex		INTEGER,
	IPAddpoolStartAdd	IpAddress,
	IPAddpoolEndAdd		IpAddress,
	GatewayAddress		IpAddress,
	IPAddLeasePeriod	INTEGER
}
				
AddPoolIndex 			OBJECT-TYPE
				SYNTAX      	INTEGER
				MAX-ACCESS  	read-only
				STATUS      	current
				DESCRIPTION
				      "DHCP Address Pool Index."
				::= { dot11DHCPIpAddressPoolEntry 1 }

IPAddpoolStartAdd		OBJECT-TYPE
				SYNTAX  IpAddress
				MAX-ACCESS read-write
				STATUS     current
				DESCRIPTION
					"IP Address pool starting address."
				::= { dot11DHCPIpAddressPoolEntry 2 }				
				
IPAddpoolEndAdd			OBJECT-TYPE
				SYNTAX  IpAddress
				MAX-ACCESS read-write
				STATUS     current
				DESCRIPTION
					"IP Address pool ending address."
				::= { dot11DHCPIpAddressPoolEntry 3 }			

GatewayAddress			OBJECT-TYPE
				SYNTAX  IpAddress
				MAX-ACCESS read-write
				STATUS     current
				DESCRIPTION
					"Gateway Address."
				::= { dot11DHCPIpAddressPoolEntry 4 }

IPAddLeasePeriod		OBJECT-TYPE
				SYNTAX  INTEGER
				MAX-ACCESS read-write
				STATUS     current
				DESCRIPTION
					"IP Address Lease Periods."
				::= { dot11DHCPIpAddressPoolEntry 5 }			    			
							
				
-- **********************************************************************

dot11DHCPIpPoolConfigTable	OBJECT-TYPE
			    	SYNTAX      SEQUENCE OF Dot11DHCPIpPoolConfigEntry
			    	MAX-ACCESS  not-accessible
			    	STATUS      current
			    	DESCRIPTION
			        	"This table shows DHCP IP Address Pool information."
			    	::= { dot11Service 5 }		
			    	
dot11DHCPIpPoolConfigEntry  	OBJECT-TYPE
			    	SYNTAX      Dot11DHCPIpPoolConfigEntry
			    	MAX-ACCESS  not-accessible
			    	STATUS      current
			    	DESCRIPTION
			        	"DHCP IP Address Pool information."
			    	INDEX { DHCPID }
			    	::= { dot11DHCPIpPoolConfigTable 1 }
			   
Dot11DHCPIpPoolConfigEntry	::=SEQUENCE{
        DHCPID                  INTEGER,
	IPPollStartAddr		IpAddress,
	IPPoolStopAddr	        IpAddress,
	GatewayAddr		IpAddress,
	Netmask	                IpAddress,
        LeasePeriod             TimeTicks,
        FirDNSServerIPAddress 	IpAddress,
        SeconDNSServerIPAddress IpAddress,
        DHCPRowStatus		RowStatus,
        DHCPPoolName		DisplayString,
        DHCPApOption43		DisplayString

}
DHCPID			OBJECT-TYPE
				SYNTAX  INTEGER
				MAX-ACCESS read-create
				STATUS     current
				DESCRIPTION
					"Create DHCPIPPOOL ID."
				::= { dot11DHCPIpPoolConfigEntry 1 }
				
IPPollStartAddr 	        OBJECT-TYPE
				SYNTAX      	IpAddress
				MAX-ACCESS  	read-create
				STATUS      	current
				DESCRIPTION
				      "IP Address pool starting address."
				::= { dot11DHCPIpPoolConfigEntry 2 }

IPPoolStopAddr		        OBJECT-TYPE
				SYNTAX  IpAddress
				MAX-ACCESS read-create
				STATUS     current
				DESCRIPTION
					"IP Address pool ending address."
				::= { dot11DHCPIpPoolConfigEntry 3 }				
				
GatewayAddr			OBJECT-TYPE
				SYNTAX  IpAddress
				MAX-ACCESS read-create
				STATUS     current
				DESCRIPTION
					"Gateway Address."
				::= { dot11DHCPIpPoolConfigEntry 4 }			

Netmask		                OBJECT-TYPE
				SYNTAX  IpAddress
				MAX-ACCESS read-create
				STATUS     current
				DESCRIPTION
					"Netmask"
				::= { dot11DHCPIpPoolConfigEntry 5 }

LeasePeriod		        OBJECT-TYPE
				SYNTAX  TimeTicks
				MAX-ACCESS read-create
				STATUS     current
				DESCRIPTION
					"IP Address Lease Periods."

				::= { dot11DHCPIpPoolConfigEntry 6 }
FirDNSServerIPAddress	        OBJECT-TYPE
				SYNTAX  IpAddress
				MAX-ACCESS read-create
				STATUS     current
				DESCRIPTION
					"IP Address first DNS IP Address."
				::= { dot11DHCPIpPoolConfigEntry 7 }
			
SeconDNSServerIPAddress	        OBJECT-TYPE
				SYNTAX  IpAddress
				MAX-ACCESS read-create
				STATUS     current
				DESCRIPTION
					"IP Address second DNS IP Address."
				::= { dot11DHCPIpPoolConfigEntry 8 }
					
DHCPRowStatus	                OBJECT-TYPE
			    	SYNTAX      RowStatus
			    	MAX-ACCESS  read-create
			    	STATUS      current
			    	DESCRIPTION
			        	"This variable is used to create, modify, and/or delete a row
			        	 in this table."
			    	::= { dot11DHCPIpPoolConfigEntry 9 }	
			    	
DHCPPoolName		        OBJECT-TYPE
				SYNTAX  DisplayString
				MAX-ACCESS read-create
				STATUS     current
				DESCRIPTION
					"DHCP pool name."
				::= { dot11DHCPIpPoolConfigEntry 10 }	

DHCPApOption43		        OBJECT-TYPE
				SYNTAX  DisplayString
				MAX-ACCESS read-create
				STATUS     current
				DESCRIPTION
					"DHCP option43 string."
				::= { dot11DHCPIpPoolConfigEntry 11 }							
dot11DHCPUseageTable		OBJECT-TYPE
			    	SYNTAX      SEQUENCE OF Dot11DHCPUseageEntry
			    	MAX-ACCESS  not-accessible
			    	STATUS      current
			    	DESCRIPTION
			        	"This table shows DHCP IP Address Pool information."
			    	::= { dot11Service 6 }		
			    	
dot11DHCPUseageEntry  	OBJECT-TYPE
			    	SYNTAX      Dot11DHCPUseageEntry
			    	MAX-ACCESS  not-accessible
			    	STATUS      current
			    	DESCRIPTION
			        	"DHCP IP Address Pool information."
			    	INDEX { DHCPUSEID }
			    	::= { dot11DHCPUseageTable 1 }	
			    	
Dot11DHCPUseageEntry	::=SEQUENCE{
        DHCPUSEID               INTEGER,
	DHCPoolName		DisplayString,
	DHCPoolUseage		INTEGER,
	DHCPMaxLimit		INTEGER,
	DHCPReqnum		Counter32,
	DHCPResponse		Counter32,
	DHCPDiscoverynum        Counter32,
	DHCPOffernum            Counter32
}	
		    	
DHCPUSEID		        OBJECT-TYPE
				SYNTAX  INTEGER
				MAX-ACCESS read-only
				STATUS     current
				DESCRIPTION
					"DHCP index."
				::= { dot11DHCPUseageEntry 1 }		
				
DHCPoolName		        OBJECT-TYPE
				SYNTAX  DisplayString
				MAX-ACCESS read-only
				STATUS     current
				DESCRIPTION
					"DHCP pool name."
				::= { dot11DHCPUseageEntry 2 }		

DHCPoolUseage		        OBJECT-TYPE
				SYNTAX  INTEGER
				MAX-ACCESS read-only
				STATUS     current
				DESCRIPTION
					"DHCP pool useage."
				::= { dot11DHCPUseageEntry 3 }		
				
DHCPMaxLimit		        OBJECT-TYPE
				SYNTAX  INTEGER
				MAX-ACCESS read-write
				STATUS     current
				DESCRIPTION
					"DHCP useage max limit."
				::= { dot11DHCPUseageEntry 4 }	
				
DHCPReqnum		        OBJECT-TYPE
				SYNTAX  Counter32
				MAX-ACCESS read-only
				STATUS     current
				DESCRIPTION
					"DHCP request num for pool."
				::= { dot11DHCPUseageEntry 5 }	
				
DHCPResponse		        OBJECT-TYPE
				SYNTAX  Counter32
				MAX-ACCESS read-only
				STATUS     current
				DESCRIPTION
					"DHCP response num for pool."
				::= { dot11DHCPUseageEntry 6 }			
DHCPDiscoverynum		        OBJECT-TYPE
				SYNTAX  Counter32
				MAX-ACCESS read-only
				STATUS     current
				DESCRIPTION
					"DHCP discovery num for pool."
				::= { dot11DHCPUseageEntry 7 }		
DHCPOffernum		        OBJECT-TYPE
				SYNTAX  Counter32
				MAX-ACCESS read-only
				STATUS     current
				DESCRIPTION
					"DHCP offer num for pool."
				::= { dot11DHCPUseageEntry 8 }	

-- **********************************************************************	
dot11DHCPIpv6PoolConfigTable		OBJECT-TYPE
			    	SYNTAX      SEQUENCE OF Dot11DHCPIpv6PoolConfigEntry
			    	MAX-ACCESS  not-accessible
			    	STATUS      current
			    	DESCRIPTION
			        	"This table shows DHCP IPV6 Address Pool information."
			    	::= { dot11Service 7 }	

dot11DHCPIpv6PoolConfigEntry  	OBJECT-TYPE
			    	SYNTAX      Dot11DHCPIpv6PoolConfigEntry
			    	MAX-ACCESS  not-accessible
			    	STATUS      current
			    	DESCRIPTION
			        	"DHCP IPV6 Address Pool information."
			    	INDEX { Ipv6DHCPID }
			    	::= { dot11DHCPIpv6PoolConfigTable 1 }
			   
Dot11DHCPIpv6PoolConfigEntry	::=SEQUENCE{
        Ipv6DHCPID              	INTEGER,
        Ipv6DHCPPoolName		DisplayString,
	IPv6PoolStartAddr		InetAddressIPv6,
	IPv6PoolStopAddr		InetAddressIPv6,
	IPv6NetPrefixLen	       	INTEGER,
        FirDNSServerIPv6Address 	InetAddressIPv6,
        SeconDNSServerIPv6Address 	InetAddressIPv6,
        Ipv6LeasePeriod            	TimeTicks,
        Ipv6DHCPRowStatus		RowStatus,
        SysIPv6GWAddr			InetAddressIPv6
}
Ipv6DHCPID			OBJECT-TYPE
				SYNTAX  INTEGER
				MAX-ACCESS read-create
				STATUS     current
				DESCRIPTION
					"Create DHCPIPv6POOL ID."
				::= { dot11DHCPIpv6PoolConfigEntry 1 }

Ipv6DHCPPoolName		OBJECT-TYPE
				SYNTAX  DisplayString
				MAX-ACCESS read-create
				STATUS     current
				DESCRIPTION
					"DHCP IPV6 pool name."
				::= { dot11DHCPIpv6PoolConfigEntry 2 }	
				
IPv6PoolStartAddr 	        OBJECT-TYPE
				SYNTAX      	InetAddressIPv6
				MAX-ACCESS  	read-create
				STATUS      	current
				DESCRIPTION
				      "IPV6 Address pool starting address."
				::= { dot11DHCPIpv6PoolConfigEntry 3 }

IPv6PoolStopAddr		OBJECT-TYPE
				SYNTAX  InetAddressIPv6
				MAX-ACCESS read-create
				STATUS     current
				DESCRIPTION
					"IPV6 Address pool ending address."
				::= { dot11DHCPIpv6PoolConfigEntry 4 }				
				
IPv6NetPrefixLen		OBJECT-TYPE
				SYNTAX  INTEGER(1..128)
				MAX-ACCESS read-create
				STATUS     current
				DESCRIPTION
					"Prefix length."
				::= { dot11DHCPIpv6PoolConfigEntry 5 }			

FirDNSServerIPv6Address	        OBJECT-TYPE
				SYNTAX  InetAddressIPv6
				MAX-ACCESS read-create
				STATUS     current
				DESCRIPTION
					"IP Address first DNS IP Address."
				::= { dot11DHCPIpv6PoolConfigEntry 6 }
			
SeconDNSServerIPv6Address	        OBJECT-TYPE
				SYNTAX  InetAddressIPv6
				MAX-ACCESS read-create
				STATUS     current
				DESCRIPTION
					"IP Address second DNS IP Address."
				::= { dot11DHCPIpv6PoolConfigEntry 7 }

Ipv6LeasePeriod		        OBJECT-TYPE
				SYNTAX  TimeTicks
				MAX-ACCESS read-create
				STATUS     current
				DESCRIPTION
					"IPv6 Address Lease Periods."

				::= { dot11DHCPIpv6PoolConfigEntry 8 }
					
Ipv6DHCPRowStatus	        OBJECT-TYPE
			    	SYNTAX      RowStatus
			    	MAX-ACCESS  read-create
			    	STATUS      current
			    	DESCRIPTION
			        	"This variable is used to create, modify, and/or delete a row
			        	 in this table."
			    	::= { dot11DHCPIpv6PoolConfigEntry 9 }	
			    	
SysIPv6GWAddr 	        OBJECT-TYPE
				SYNTAX      	InetAddressIPv6
				MAX-ACCESS  	read-only
				STATUS      	current
				DESCRIPTION
				      "AP IPV6 Gateway address."
				::= { dot11DHCPIpv6PoolConfigEntry 10 }

dot11DHCPIpv6UseageTable		OBJECT-TYPE
			    	SYNTAX      SEQUENCE OF Dot11DHCPIpv6UseageEntry
			    	MAX-ACCESS  not-accessible
			    	STATUS      current
			    	DESCRIPTION
			        	"This table shows DHCP IPV6 Address Pool information."
			    	::= { dot11Service 8 }		
			    	
dot11DHCPIpv6UseageEntry  	OBJECT-TYPE
			    	SYNTAX      Dot11DHCPIpv6UseageEntry
			    	MAX-ACCESS  not-accessible
			    	STATUS      current
			    	DESCRIPTION
			        	"DHCP IPV6 Address Pool information."
			    	INDEX { Ipv6DHCPUSEID }
			    	::= { dot11DHCPIpv6UseageTable 1 }	
			    	
Dot11DHCPIpv6UseageEntry	::=SEQUENCE{
        Ipv6DHCPUSEID              	INTEGER,
	DHCPIpv6poolName		DisplayString,
	DHCPIpv6PoolUseage		INTEGER,
	DHCPIpv6ReqTimes		Counter32,
	DHCPIpv6ReqSucTimes		Counter32
}	
Ipv6DHCPUSEID			OBJECT-TYPE
				SYNTAX  INTEGER
				MAX-ACCESS read-only
				STATUS     current
				DESCRIPTION
					"Create DHCPIPv6POOL ID."
				::= { dot11DHCPIpv6UseageEntry 1 }  	
				
DHCPIpv6poolName		 OBJECT-TYPE
				SYNTAX  DisplayString
				MAX-ACCESS read-only
				STATUS     current
				DESCRIPTION
					"DHCP IPV6 pool name."
				::= { dot11DHCPIpv6UseageEntry 2 }		

DHCPIpv6PoolUseage		OBJECT-TYPE
				SYNTAX  INTEGER
				MAX-ACCESS read-only
				STATUS     current
				DESCRIPTION
					"DHCP IPV6 pool useage."
				::= { dot11DHCPIpv6UseageEntry 3 }
														
-- **********************************************************************
-- * dot11AlarmConfiguration
-- **********************************************************************

dot11AlarmConfiguration 	OBJECT IDENTIFIER ::={ dot11AcGroup 18}

dot11TrapAllSwitchGroup OBJECT IDENTIFIER ::={ dot11AlarmConfiguration 1 }
APInterfNumThreshhd		OBJECT-TYPE
				SYNTAX  INTEGER(1..200)
				MAX-ACCESS  read-write
				STATUS  current
				DESCRIPTION
					"AP interference alarm threshold."
				::= { dot11TrapAllSwitchGroup  1}

StaInterfNumThreshhd		OBJECT-TYPE
				SYNTAX	INTEGER
				MAX-ACCESS  read-write
				STATUS  current
				DESCRIPTION
					"Station interference alarm threshold."
				::= { dot11TrapAllSwitchGroup  2}

TrapResendWaitingTime  		OBJECT-TYPE
				SYNTAX  INTEGER(0..65535)
				MAX-ACCESS  read-write
				STATUS  current
				DESCRIPTION
					"Trap resend wait time,range is 0-65535 seconds."
				::= { dot11TrapAllSwitchGroup  3}
				
TrapResendWaitingTimes 		OBJECT-TYPE
				SYNTAX  INTEGER(0..50)
				MAX-ACCESS  read-write
				STATUS  current
				DESCRIPTION
					"Trap resend wait times,range is 0-50."
				::= { dot11TrapAllSwitchGroup  4}				
	
	
				
dot11ConfigTrapSwitchTable OBJECT-TYPE
	    SYNTAX      SEQUENCE OF Dot11ConfigTrapSwitchEntry
	    MAX-ACCESS  not-accessible
	    STATUS      current
	    DESCRIPTION
	        "Shows Trap Destination IP Address Group."
	    ::= { dot11AlarmConfiguration 2 }
dot11ConfigTrapSwitchEntry  OBJECT-TYPE
    SYNTAX      Dot11ConfigTrapSwitchEntry
    MAX-ACCESS  not-accessible
    STATUS      current
    DESCRIPTION
        "Config Trap Destination IP Address Group."
    INDEX { wtpMacAddr }
    ::= { dot11ConfigTrapSwitchTable 1 }
   
Dot11ConfigTrapSwitchEntry ::=SEQUENCE{
                wtpMacAddr      	DisplayString,
		APInterfThreshhd	INTEGER,
		StaInterfThreshhd	INTEGER,
		CPUusageThreshhd	INTEGER,
		MemUsageThreshhd	INTEGER,
		CoChAPInterfThreshhd	INTEGER,
		AdjacentChAPInterfThreshhd	INTEGER
}
wtpMacAddr	                OBJECT-TYPE
				SYNTAX     DisplayString
				MAX-ACCESS read-only
				STATUS     current
				DESCRIPTION
					"AP Mac  Address Group."
				::= { dot11ConfigTrapSwitchEntry 1 }
APInterfThreshhd	            OBJECT-TYPE
				SYNTAX     INTEGER
				MAX-ACCESS read-write
				STATUS     current
				DESCRIPTION
					"AP Interference NumThreshhd."
				::= { dot11ConfigTrapSwitchEntry 2 }
StaInterfThreshhd	        OBJECT-TYPE
				SYNTAX     INTEGER
				MAX-ACCESS read-write
				STATUS     current
				DESCRIPTION
					"Station Interference Threshhd."
				::= { dot11ConfigTrapSwitchEntry 3 }
CPUusageThreshhd	        OBJECT-TYPE
				SYNTAX     INTEGER(1..9999)
				MAX-ACCESS read-write
				STATUS     current
				DESCRIPTION
					"AP CPU Threshhd."
				::= { dot11ConfigTrapSwitchEntry 4 }
MemUsageThreshhd	        OBJECT-TYPE
				SYNTAX     INTEGER(1..99)
				MAX-ACCESS read-write
				STATUS     current
				DESCRIPTION
					"AP Memory Threshhd."
				::= { dot11ConfigTrapSwitchEntry 5 }
CoChAPInterfThreshhd	        OBJECT-TYPE
				SYNTAX     INTEGER(0..-120)
				MAX-ACCESS read-write
				STATUS     current
				DESCRIPTION
					"AP interf of the same channel."
				::= { dot11ConfigTrapSwitchEntry 6 }
AdjacentChAPInterfThreshhd	        OBJECT-TYPE
				SYNTAX     INTEGER(0..-120)
				MAX-ACCESS read-write
				STATUS     current
				DESCRIPTION
					"AP interf of Adjacent Channel."
				::= { dot11ConfigTrapSwitchEntry 7 }
				
--**************************here add new mib table:ping table**************************************************************
--dot11Tools	OBJECT IDENTIFIER ::={ dot11AcGroup 18 }
--dot11PingTable OBJECT-TYPE
--	    SYNTAX      SEQUENCE OF Dot11PingEntry
--	    MAX-ACCESS  not-accessible
--	    STATUS      current
--	    DESCRIPTION
--	        "Ping."
--	    ::= { dot11Tools 1 }

--dot11PingEntry  OBJECT-TYPE
--   SYNTAX      Dot11PingEntry
--    MAX-ACCESS  not-accessible
--    STATUS      current
--    DESCRIPTION
--        "Ping."
--    INDEX { dot11PingIndex }
--    ::= { dot11PingTable 1 }
   
--Dot11PingEntry ::=SEQUENCE{
--		    dot11PingIndex	 	INTEGER,
--		    dot11PingAddress 		DisplayString,
--		    dot11PingResult 	        TruthValue,
--		    dot11PingEntryStatus 	RowStatus
--}
--dot11PingIndex			OBJECT-TYPE
--				SYNTAX  INTEGER
--				MAX-ACCESS read-create
--				STATUS     current
--				DESCRIPTION
--					"Ping index."
--				::= { dot11PingEntry 1 }

--dot11PingAddress		OBJECT-TYPE
--				SYNTAX  DisplayString
--				MAX-ACCESS read-create
--				STATUS     current
--				DESCRIPTION
--					"Ping address."
--				::= { dot11PingEntry 2 }

--dot11PingResult			OBJECT-TYPE
--				SYNTAX  TruthValue
--				MAX-ACCESS read-create
--				STATUS     current
--				DESCRIPTION
--					"Whether can reach the destination."
--				::= { dot11PingEntry 3 }

--dot11PingEntryStatus		OBJECT-TYPE
--				SYNTAX  RowStatus
--				MAX-ACCESS read-create
--				STATUS     current
--				DESCRIPTION
--					"This variable is used to create, modify, and/or delete a row
--		        	 	in this table."
--				::= { dot11PingEntry 4 }

--************************************************************************************************************************	

--*********************************************************************************

dot11ConfigTrapGroup OBJECT IDENTIFIER ::={ dot11AcGroup 19 }

dot11ConfigTrapGroupTable OBJECT-TYPE
	    SYNTAX      SEQUENCE OF Dot11ConfigTrapGroupEntry
	    MAX-ACCESS  not-accessible
	    STATUS      current
	    DESCRIPTION
	        "Shows Trap Destination IP Address Group."
	    ::= { dot11ConfigTrapGroup 1 }

dot11ConfigTrapGroupEntry  OBJECT-TYPE
    SYNTAX      Dot11ConfigTrapGroupEntry
    MAX-ACCESS  not-accessible
    STATUS      current
    DESCRIPTION
        "Config Trap Destination IP Address Group."
    INDEX { TrapID }
    ::= { dot11ConfigTrapGroupTable 1 }
   
Dot11ConfigTrapGroupEntry ::=SEQUENCE{
                TrapID       		INTEGER,
                TrapName		DisplayString,
                TrapVersion		INTEGER,
		TrapSourIPAddress	IpAddress,
		TrapDestIPAddress	IpAddress,
		TrapCommunity		DisplayString,
		TrapState		INTEGER,
		TrapDestPort		INTEGER,
		TrapRowStatus   	RowStatus
}
TrapID	                	OBJECT-TYPE
				SYNTAX     INTEGER
				MAX-ACCESS read-create
				STATUS     current
				DESCRIPTION
					"Trap ID."
				::= { dot11ConfigTrapGroupEntry 1 }
				
TrapName	                OBJECT-TYPE
				SYNTAX     DisplayString(SIZE(1..30))
				MAX-ACCESS read-create
				STATUS     current
				DESCRIPTION
					"Trap Name,the lenth of trap name should be 1 to 30,
					trap name should be ASCII value in the Non-control characters (Spaces except)."
				::= { dot11ConfigTrapGroupEntry 2 }	
				
TrapVersion			OBJECT-TYPE
				SYNTAX     INTEGER{
                                                  v1(1),
                                                  v2c(2),
                                                  v3(3)
                                                   }
				MAX-ACCESS read-create
				STATUS     current
				DESCRIPTION
					"Trap Version."
				::= { dot11ConfigTrapGroupEntry 3 }							

TrapSourIPAddress	        OBJECT-TYPE
				SYNTAX     IpAddress
				MAX-ACCESS read-create
				STATUS     current
				DESCRIPTION
					"Trap Source IP Address,optional."
				::= { dot11ConfigTrapGroupEntry 4 }
				
TrapDestIPAddress	        OBJECT-TYPE
				SYNTAX     IpAddress
				MAX-ACCESS read-create
				STATUS     current
				DESCRIPTION
					"Trap Destination IP Address."
				::= { dot11ConfigTrapGroupEntry 5 }									
				
TrapCommunity	                OBJECT-TYPE
				SYNTAX     DisplayString(SIZE(1..20))
				MAX-ACCESS read-create
				STATUS     current
				DESCRIPTION
					"Trap Name,The lenth of community name should be 1 to 20,
					community name should be ASCII value in the Non-control characters (Spaces except),
					and it's can't begin with #,double quotes,single quotes,
					\ only appeared in end"
				::= { dot11ConfigTrapGroupEntry 6 }					
				
TrapState			OBJECT-TYPE
				SYNTAX     INTEGER{
                                                  enable(1),
                                                  disable(0)
                                                   }
				MAX-ACCESS read-create
				STATUS     current
				DESCRIPTION
					"Trap State."
				::= { dot11ConfigTrapGroupEntry 7 }					
				
TrapDestPort			OBJECT-TYPE
				SYNTAX     INTEGER(1..65535)
				MAX-ACCESS read-create
				STATUS     current
				DESCRIPTION
					"Trap Destination Port,optional,default is 162."
				::= { dot11ConfigTrapGroupEntry 8 }				

TrapRowStatus	                OBJECT-TYPE
			    	SYNTAX      RowStatus
			    	MAX-ACCESS  read-create
			    	STATUS      current
			    	DESCRIPTION
			        	"This variable is used to create, modify, and/or delete a row
			        	 in this table."
			    	::= { dot11ConfigTrapGroupEntry 9 }

						
dot11TotalNasIDGroup OBJECT IDENTIFIER ::={ dot11AcGroup 20 }

TotalNasID	                OBJECT-TYPE
				SYNTAX     INTEGER
				MAX-ACCESS read-only
				STATUS     current
				DESCRIPTION
					"Total Nas ID num."
				::= { dot11TotalNasIDGroup 1 }

				
DefaultNasID	                OBJECT-TYPE
				SYNTAX     DisplayString
				MAX-ACCESS read-write
				STATUS     current
				DESCRIPTION
					"default Nas ID. If eag is started, can not set it"
				::= { dot11TotalNasIDGroup 2 }


dot11ConfigNasGroup OBJECT IDENTIFIER ::={ dot11AcGroup 21 }

dot11ConfigNasGroupTable OBJECT-TYPE
	    SYNTAX      SEQUENCE OF Dot11ConfigNasGroupEntry
	    MAX-ACCESS  not-accessible
	    STATUS      current
	    DESCRIPTION
	        "Shows config NAS Group."
	    ::= { dot11ConfigNasGroup 1 }

dot11ConfigNasGroupEntry  OBJECT-TYPE
    SYNTAX      Dot11ConfigNasGroupEntry
    MAX-ACCESS  not-accessible
    STATUS      current
    DESCRIPTION
        "Config Nas Group."
    INDEX { NasID }
    ::= { dot11ConfigNasGroupTable 1 }
   
Dot11ConfigNasGroupEntry ::=SEQUENCE{
                NasID         		INTEGER,
		NasName	      		DisplayString,
		NasRowStatus  		RowStatus,
		NasKeyType    		INTEGER,
		NasKeyValue   		DisplayString,
		NasSyntaxisPoint	INTEGER
}
NasID	                        OBJECT-TYPE
				SYNTAX     INTEGER
				MAX-ACCESS read-create
				STATUS     current
				DESCRIPTION
					"NasID   Group."
				::= { dot11ConfigNasGroupEntry 1 }

NasName	                        OBJECT-TYPE
				SYNTAX     DisplayString
				MAX-ACCESS read-create
				STATUS     current
				DESCRIPTION
					"NasID   name."
				::= { dot11ConfigNasGroupEntry 2 }

NasRowStatus	                OBJECT-TYPE
			    	SYNTAX      RowStatus
			    	MAX-ACCESS  read-create
			    	STATUS      current
			    	DESCRIPTION
			        	"This variable is used to create, modify, and/or delete a row
			        	 in this table."
			    	::= { dot11ConfigNasGroupEntry 3 }
			    	
NasKeyType 			OBJECT-TYPE
				SYNTAX     INTEGER{
						wlanid(0),
						vlanid(1),
						wtpid(2),
						iprange(3),
						interface(4)
						} 
				MAX-ACCESS read-create
				STATUS     current
				DESCRIPTION
			        	"NasID KeyType."
				::= { dot11ConfigNasGroupEntry 4 }	
				
NasKeyValue	                OBJECT-TYPE
				SYNTAX     DisplayString
				MAX-ACCESS read-create
				STATUS     current
				DESCRIPTION
					"NasID KeyValue,key value depends on key type.If key type is iprange(3),
					the form of key value should be A.B.C.D or A1.B1.C1.D1-A2.B2.C3.D2"
				::= { dot11ConfigNasGroupEntry 5 }		
				
NasSyntaxisPoint                OBJECT-TYPE
				SYNTAX     INTEGER(0..99)
				MAX-ACCESS read-create
				STATUS     current
				DESCRIPTION
					"NasID   Group."
				::= { dot11ConfigNasGroupEntry 6 }							    	

dot11NasPortTable OBJECT-TYPE
	    SYNTAX      SEQUENCE OF dot11NasPortEntry
	    MAX-ACCESS  not-accessible
	    STATUS      current
	    DESCRIPTION
	        "Show Nas Port ID Group."
	    ::= { dot11ConfigNasGroup 2 }
dot11NasPortEntry  OBJECT-TYPE
    SYNTAX      dot11NasPortEntry
    MAX-ACCESS  not-accessible
    STATUS      current
    DESCRIPTION
        "Shows Nas Port ID Group."
    INDEX { wtpMacAddr, 
    		wlanID}
    ::= { dot11NasPortTable 1 } 
dot11NasPortEntry ::=SEQUENCE{
                NasPortID         DisplayString
}
NasPortID	                OBJECT-TYPE
				SYNTAX     DisplayString
				MAX-ACCESS read-only
				STATUS     current
				DESCRIPTION
					"Nas Port ID."
				::= { dot11NasPortEntry 1 }


dot11NewNasPortTable OBJECT-TYPE
	    SYNTAX      SEQUENCE OF Dot11NewNasPortEntry
	    MAX-ACCESS  not-accessible
	    STATUS      current
	    DESCRIPTION
	        "Show New Nas Port ID Group."
	    ::= { dot11ConfigNasGroup 3 }
dot11NewNasPortEntry  OBJECT-TYPE
    SYNTAX      Dot11NewNasPortEntry
    MAX-ACCESS  not-accessible
    STATUS      current
    DESCRIPTION
        "Shows New Nas Port ID Group."
    INDEX { wtpMacAddr,
              RadioLoID,
		wlanId }
    ::= { dot11NewNasPortTable 1 } 
Dot11NewNasPortEntry ::=SEQUENCE{
                NewNasPortID         DisplayString
}
NewNasPortID	                OBJECT-TYPE
				SYNTAX     DisplayString
				MAX-ACCESS read-only
				STATUS     current
				DESCRIPTION
					"New Nas Port ID."
				::= { dot11NewNasPortEntry 1 }


				
dot11ConfigVlanGroup OBJECT IDENTIFIER ::={ dot11AcGroup 22 }

dot11ConfigVlanGroupTable OBJECT-TYPE
	    SYNTAX      SEQUENCE OF Dot11ConfigVlanGroupEntry
	    MAX-ACCESS  not-accessible
	    STATUS      current
	    DESCRIPTION
	        "Shows config Vlan Group."
	    ::= { dot11ConfigVlanGroup 1 }
dot11ConfigVlanGroupEntry  OBJECT-TYPE
    SYNTAX      Dot11ConfigVlanGroupEntry
    MAX-ACCESS  not-accessible
    STATUS      current
    DESCRIPTION
        "Config Vlan Group."
    INDEX { VlanID }
    ::= { dot11ConfigVlanGroupTable 1 }
   
Dot11ConfigVlanGroupEntry ::=SEQUENCE{
                VlanID                   INTEGER,
		Port	                 DisplayString,
                VlanDescr                DisplayString,
                InterfIndex              INTEGER,
                ConfigVlanRowStatus      RowStatus
}
VlanID	                        OBJECT-TYPE
				SYNTAX     INTEGER
				MAX-ACCESS read-create
				STATUS     current
				DESCRIPTION
					"VlanID   Group."
				::= { dot11ConfigVlanGroupEntry 1 }

Port                            OBJECT-TYPE
				SYNTAX     DisplayString
				MAX-ACCESS read-create
				STATUS     current
				DESCRIPTION
					"Vlan   Port."
				::= { dot11ConfigVlanGroupEntry 2 }

VlanDescr                            OBJECT-TYPE
				SYNTAX     DisplayString
				MAX-ACCESS read-create
				STATUS     current
				DESCRIPTION
					"VlanDescr."
				::= { dot11ConfigVlanGroupEntry 3 }
InterfIndex                            OBJECT-TYPE
				SYNTAX     INTEGER
				MAX-ACCESS read-create
				STATUS     current
				DESCRIPTION
					"InterfIndex."
				::= { dot11ConfigVlanGroupEntry  4 }
ConfigVlanRowStatus	                OBJECT-TYPE
			    	SYNTAX      RowStatus
			    	MAX-ACCESS  read-create
			    	STATUS      current
			    	DESCRIPTION
			        	"This variable is used to create, modify, and/or delete a row
			        	 in this table."
			    	::= { dot11ConfigVlanGroupEntry 5 }

dot11NewConfigVlanGroupTable OBJECT-TYPE
	    SYNTAX      SEQUENCE OF Dot11NewConfigVlanGroupEntry
	    MAX-ACCESS  not-accessible
	    STATUS      current
	    DESCRIPTION
	        "Shows NewVlan Group."
	    ::= { dot11ConfigVlanGroup 2 }
dot11NewConfigVlanGroupEntry  OBJECT-TYPE
    SYNTAX      Dot11NewConfigVlanGroupEntry
    MAX-ACCESS  not-accessible
    STATUS      current
    DESCRIPTION
        "NewVlan Group."
    INDEX { NewVlanID }
    ::= { dot11NewConfigVlanGroupTable 1 }
   
Dot11NewConfigVlanGroupEntry ::=SEQUENCE{
                NewVlanID                   INTEGER,
		NewPort	            DisplayString,
                NewVlanName                DisplayString,
                NewConfigVlanRowStatus      RowStatus
}
NewVlanID	                        OBJECT-TYPE
				SYNTAX     INTEGER
				MAX-ACCESS read-create
				STATUS     current
				DESCRIPTION
					"NewVlanID   Group."
				::= { dot11NewConfigVlanGroupEntry 1 }

NewPort                            OBJECT-TYPE
				SYNTAX     DisplayString
				MAX-ACCESS read-create
				STATUS     current
				DESCRIPTION
					"NewVlan  Port."
				::= { dot11NewConfigVlanGroupEntry 2 }

NewVlanName                            OBJECT-TYPE
				SYNTAX     DisplayString
				MAX-ACCESS read-create
				STATUS     current
				DESCRIPTION
					"NewVlan   Name."
				::= { dot11NewConfigVlanGroupEntry 3 }
NewConfigVlanRowStatus	                OBJECT-TYPE
			    	SYNTAX      RowStatus
			    	MAX-ACCESS  read-create
			    	STATUS      current
			    	DESCRIPTION
			        	"This variable is used to create, modify, and/or delete a row
			        	 in this table."
			    	::= { dot11NewConfigVlanGroupEntry 4 }






dot11ConfigPortalServerGroup OBJECT IDENTIFIER ::={ dot11AcGroup 23 }

dot11ConfigPortalServerGroupTable OBJECT-TYPE
	    SYNTAX      SEQUENCE OF Dot11ConfigPortalServerGroupEntry
	    MAX-ACCESS  not-accessible
	    STATUS      current
	    DESCRIPTION
	        "Shows config Portal Server."
	    ::= { dot11ConfigPortalServerGroup 1 }

dot11ConfigPortalServerGroupEntry  OBJECT-TYPE
    SYNTAX      Dot11ConfigPortalServerGroupEntry
    MAX-ACCESS  not-accessible
    STATUS      current
    DESCRIPTION
        "Config Portal Server."
    INDEX { PortalIndex }
    ::= { dot11ConfigPortalServerGroupTable 1 }
   
Dot11ConfigPortalServerGroupEntry ::=SEQUENCE{		
		PortalKey     		DisplayString,
		PortalURL      		DisplayString,
		PortalPort     		INTEGER,
		PortalIndex		INTEGER,                
                PortalDomain   		DisplayString,
                PortalRowStatus 	RowStatus,
                PortalKeyType		INTEGER
}
PortalKey	                OBJECT-TYPE
				SYNTAX     DisplayString
				MAX-ACCESS read-create
				STATUS     current
				DESCRIPTION
					"Portal Key."
				::= { dot11ConfigPortalServerGroupEntry 1 }
				
PortalURL	                OBJECT-TYPE
				SYNTAX     DisplayString
				MAX-ACCESS read-create
				STATUS     current
				DESCRIPTION
					"Portal URL."
				::= { dot11ConfigPortalServerGroupEntry 2 }	
				
PortalPort	                OBJECT-TYPE
				SYNTAX     INTEGER(1..65535)
				MAX-ACCESS read-create
				STATUS     current
				DESCRIPTION
					"Portal Port."
				::= { dot11ConfigPortalServerGroupEntry 3 }							
				
PortalIndex                     OBJECT-TYPE
				SYNTAX     INTEGER
				MAX-ACCESS read-create
				STATUS     current
				DESCRIPTION
					"Portal Index."
				::= { dot11ConfigPortalServerGroupEntry 4 }
				
PortalDomain	                OBJECT-TYPE
				SYNTAX     DisplayString
				MAX-ACCESS read-create
				STATUS     current
				DESCRIPTION
					"Portal Domain."
				::= { dot11ConfigPortalServerGroupEntry 5 }

PortalRowStatus	                OBJECT-TYPE
			    	SYNTAX      RowStatus
			    	MAX-ACCESS  read-create
			    	STATUS      current
			    	DESCRIPTION
			        	"This variable is used to create, modify, and/or delete a row
			        	 in this table."
			    	::= { dot11ConfigPortalServerGroupEntry 6 }				

PortalKeyType 			OBJECT-TYPE
				SYNTAX     INTEGER{
						essid(0),
						wlanid(1),
						vlanid(2),
						wtpid(3),
						interface(4)						
						} 
				MAX-ACCESS read-create
				STATUS     current
				DESCRIPTION
			        	"Portal KeyType."
				::= { dot11ConfigPortalServerGroupEntry 7 }
								
			    	
dot11PortalWhiteListTable  	OBJECT-TYPE
	    SYNTAX      SEQUENCE OF Dot11PortalWhiteListEntry
	    MAX-ACCESS  not-accessible
	    STATUS      current
	    DESCRIPTION
	        "Shows config Portal Server."
	    ::= { dot11ConfigPortalServerGroup 2 }

dot11PortalWhiteListEntry  OBJECT-TYPE
    SYNTAX      Dot11PortalWhiteListEntry
    MAX-ACCESS  not-accessible
    STATUS      current
    DESCRIPTION
        "Config Portal Server."
    INDEX { WLid }
    ::= { dot11PortalWhiteListTable 1 }
   
Dot11PortalWhiteListEntry ::=SEQUENCE{
		WLid		INTEGER,
		WLtype		INTEGER,
                WLstartip       IpAddress,
                WLendip      	IpAddress,		
                WLport   	DisplayString,
                WLURL           DisplayString,
                WLRowStatus     RowStatus                            
                }
WLid  	                	OBJECT-TYPE
				SYNTAX     INTEGER
				MAX-ACCESS read-create
				STATUS     current
				DESCRIPTION
					"white list index."     
				::= { dot11PortalWhiteListEntry 1 }
				
WLtype  	                OBJECT-TYPE
				SYNTAX     INTEGER{
						ip(0),
						domain(1)					
						} 
				MAX-ACCESS read-create
				STATUS     current
				DESCRIPTION
					"white list type.
					if the white list type is ip,WLstartip must set to be applied to the white list.
					if the white list type is domain,domain url must set to be applied to the white list"     
				::= { dot11PortalWhiteListEntry 2 }
										          
WLstartip  	                OBJECT-TYPE
				SYNTAX     IpAddress
				MAX-ACCESS read-create
				STATUS     current
				DESCRIPTION
					"white list start ip."
				::= { dot11PortalWhiteListEntry 3 }
				
WLendip	                	OBJECT-TYPE
				SYNTAX     IpAddress
				MAX-ACCESS read-create
				STATUS     current
				DESCRIPTION
					"white list end ip,optional."
				::= { dot11PortalWhiteListEntry 4 }
				
WLport	                	OBJECT-TYPE
				SYNTAX     DisplayString
				MAX-ACCESS read-create
				STATUS     current
				DESCRIPTION
					"white list port list,the format is (all|PORT[,PORT]...),optional"
				::= { dot11PortalWhiteListEntry 5 }
				
WLURL	                        OBJECT-TYPE
				SYNTAX     DisplayString
				MAX-ACCESS read-create
				STATUS     current
				DESCRIPTION
					"white list URL."
				::= { dot11PortalWhiteListEntry 6 }				

WLRowStatus	                OBJECT-TYPE
			    	SYNTAX      RowStatus
			    	MAX-ACCESS  read-create
			    	STATUS      current
			    	DESCRIPTION
			        	"This variable is used to create, modify, and/or delete a row
			        	 in this table."
			    	::= { dot11PortalWhiteListEntry 7 }


dot11PortalBlackListTable OBJECT-TYPE
	    SYNTAX      SEQUENCE OF Dot11PortalBlackListEntry
	    MAX-ACCESS  not-accessible
	    STATUS      current
	    DESCRIPTION
	        "Shows config Portal Server."
	    ::= { dot11ConfigPortalServerGroup 3 }

dot11PortalBlackListEntry  OBJECT-TYPE
    SYNTAX      Dot11PortalBlackListEntry
    MAX-ACCESS  not-accessible
    STATUS      current
    DESCRIPTION
        "Config Portal Server."
    INDEX { BLid }
    ::= { dot11PortalBlackListTable 1 }
   
Dot11PortalBlackListEntry ::=SEQUENCE{	
		BLid  		INTEGER,
		BLtype		INTEGER,
                BLstartip       IpAddress,
                BLendip      	IpAddress,		
                BLport   	DisplayString,
                BLURL           DisplayString,
                BLRowStatus     RowStatus                                  
                }                     
BLid	  	                OBJECT-TYPE
				SYNTAX     INTEGER
				MAX-ACCESS read-create
				STATUS     current
				DESCRIPTION
					"black list index."
				::= { dot11PortalBlackListEntry 1 }                 
				
BLtype  	                OBJECT-TYPE
				SYNTAX     INTEGER{
						ip(0),
						domain(1)					
						} 
				MAX-ACCESS read-create
				STATUS     current
				DESCRIPTION
					"black list type.
					if the black list type is ip,BLstartip must set to be applied to the black list.
					if the black list type is domain,domain url must set to be applied to the black list"     
				::= { dot11PortalBlackListEntry 2 }
								
BLstartip  	                OBJECT-TYPE
				SYNTAX     IpAddress
				MAX-ACCESS read-create
				STATUS     current
				DESCRIPTION
					"black list start ip."
				::= { dot11PortalBlackListEntry 3 }
				
BLendip	                	OBJECT-TYPE
				SYNTAX     IpAddress
				MAX-ACCESS read-create
				STATUS     current
				DESCRIPTION
					"black list end ip,optional."
				::= { dot11PortalBlackListEntry 4 }
				
BLport	                	OBJECT-TYPE
				SYNTAX     DisplayString
				MAX-ACCESS read-create
				STATUS     current
				DESCRIPTION
					"black list port,the format is (all|PORT[,PORT]...),optional"
				::= { dot11PortalBlackListEntry 5 }
				
BLURL	                        OBJECT-TYPE
				SYNTAX     DisplayString
				MAX-ACCESS read-create
				STATUS     current
				DESCRIPTION
					"black list URL."
				::= { dot11PortalBlackListEntry 6 }				

BLRowStatus	                OBJECT-TYPE
			    	SYNTAX      RowStatus
			    	MAX-ACCESS  read-create
			    	STATUS      current
			    	DESCRIPTION
			        	"This variable is used to create, modify, and/or delete a row
			        	 in this table."
			    	::= { dot11PortalBlackListEntry 7 }



dot11ConfigEagServerGroupTable OBJECT-TYPE
	    SYNTAX      SEQUENCE OF Dot11ConfigEagServerGroupEntry
	    MAX-ACCESS  not-accessible
	    STATUS      current
	    DESCRIPTION
	        "Shows config Eag Server."
	    ::= { dot11ConfigPortalServerGroup 4 }

dot11ConfigEagServerGroupEntry  OBJECT-TYPE
    SYNTAX      Dot11ConfigEagServerGroupEntry
    MAX-ACCESS  not-accessible
    STATUS      current
    DESCRIPTION
        "Config Eag Server."
    INDEX { InstanceId}
    ::= { dot11ConfigEagServerGroupTable 1 }
   
Dot11ConfigEagServerGroupEntry ::=SEQUENCE{	
		InstanceId  				INTEGER,
		RedirListen					IpAddress,
		RedirListenPort				INTEGER,
		EagEnable					INTEGER,
		IdleTimeFunction			INTEGER,
		DebugLog					INTEGER,
		JustAllowWirelessUserLogin	INTEGER,
		RadiusAcctInterval			INTEGER,
		MaxIdleTime					INTEGER,
		MaxIdleFlow					INTEGER,
		VrrpId						INTEGER,
		PortalInteractivePort		INTEGER,
		MaxHttpResponse				INTEGER,
		AutoCreateUserSession		INTEGER
                }                     
InstanceId	  	                OBJECT-TYPE
				SYNTAX     INTEGER
				MAX-ACCESS read-only
				STATUS     current
				DESCRIPTION
					"eag instance index."
				::= { dot11ConfigEagServerGroupEntry 1 }

RedirListen	  	                OBJECT-TYPE
				SYNTAX     IpAddress
				MAX-ACCESS read-write
				STATUS     current
				DESCRIPTION
					"eag redirListen ip."
				::= { dot11ConfigEagServerGroupEntry 2 }

RedirListenPort	  	                OBJECT-TYPE
				SYNTAX     INTEGER
				MAX-ACCESS read-write
				STATUS     current
				DESCRIPTION
					"eag redirListen Port."
				::= { dot11ConfigEagServerGroupEntry 3 }	
				
EagEnable              OBJECT-TYPE
				SYNTAX     INTEGER{
						true(1),
						false(2)					 
						 }
				MAX-ACCESS read-write
				STATUS     current
				DESCRIPTION
					 "Whether to open the eag service." 
				::= { dot11ConfigEagServerGroupEntry 4 }

IdleTimeFunction        OBJECT-TYPE
				SYNTAX     INTEGER{
						true(1),
						false(2)					 
						 }
				MAX-ACCESS read-write
				STATUS     current
				DESCRIPTION
					 "Whether to open the idle time function." 
				::= { dot11ConfigEagServerGroupEntry 5 }

DebugLog        OBJECT-TYPE
				SYNTAX     INTEGER{
						true(1),
						false(2)					 
						 }
				MAX-ACCESS read-write
				STATUS     current
				DESCRIPTION
					 "Whether to open the debug log." 
				::= { dot11ConfigEagServerGroupEntry 6 }

JustAllowWirelessUserLogin        OBJECT-TYPE
				SYNTAX     INTEGER{
						true(1),
						false(2)					 
						 }
				MAX-ACCESS read-write
				STATUS     current
				DESCRIPTION
					 "Just Allow Wireless User Login." 
				::= { dot11ConfigEagServerGroupEntry 7 }

RadiusAcctInterval        OBJECT-TYPE
				SYNTAX     INTEGER(60..3600)
				MAX-ACCESS read-write
				STATUS     current
				DESCRIPTION
					 "Radius acct interval." 
				::= { dot11ConfigEagServerGroupEntry 8 }

MaxIdleTime        OBJECT-TYPE
				SYNTAX     INTEGER(60..86400)
				MAX-ACCESS read-write
				STATUS     current
				DESCRIPTION
					 "Max Idle Time." 
				::= { dot11ConfigEagServerGroupEntry 9 }
				
MaxIdleFlow        OBJECT-TYPE
				SYNTAX     INTEGER(0..10485760)
				MAX-ACCESS read-write
				STATUS     current
				DESCRIPTION
					 "Max Idle Flow." 
				::= { dot11ConfigEagServerGroupEntry 10 }
				
VrrpId        OBJECT-TYPE
				SYNTAX     INTEGER
				MAX-ACCESS read-write
				STATUS     current
				DESCRIPTION
					 "Vrrp id." 
				::= { dot11ConfigEagServerGroupEntry 11 }
				
PortalInteractivePort        OBJECT-TYPE
				SYNTAX     INTEGER(1..65535)
				MAX-ACCESS read-write
				STATUS     current
				DESCRIPTION
					 "Portal interactive port." 
				::= { dot11ConfigEagServerGroupEntry 12 }
				
MaxHttpResponse        OBJECT-TYPE
				SYNTAX     INTEGER
				MAX-ACCESS read-write
				STATUS     current
				DESCRIPTION
					 "Max http response per 5 seconds." 
				::= { dot11ConfigEagServerGroupEntry 13 }
				
AutoCreateUserSession        OBJECT-TYPE
				SYNTAX     INTEGER{
						true(1),
						false(2)					 
						 }
				MAX-ACCESS read-write
				STATUS     current
				DESCRIPTION
					 "Auto create user session." 
				::= { dot11ConfigEagServerGroupEntry 14}
				
				
dot11PortalNoAuthenticatedTable OBJECT-TYPE
	    SYNTAX      SEQUENCE OF Dot11PortalNoAuthenticatedEntry
	    MAX-ACCESS  not-accessible
	    STATUS      current
	    DESCRIPTION
	        "This table config Portal NoAuthenticated Switch."
	    ::= { dot11ConfigPortalServerGroup 5 }

dot11PortalNoAuthenticatedEntry  OBJECT-TYPE
    SYNTAX      Dot11PortalNoAuthenticatedEntry
    MAX-ACCESS  not-accessible
    STATUS      current
    DESCRIPTION
        "Config Portal Server."
    INDEX { CaptiveId,
            CaptiveInterface }
    ::= { dot11PortalNoAuthenticatedTable 1 }
   
Dot11PortalNoAuthenticatedEntry ::=SEQUENCE{	
		CaptiveId			INTEGER,
		CaptiveInterface		DisplayString,
		NoAuthRowStatus			RowStatus
                }          
CaptiveId  	                OBJECT-TYPE
				SYNTAX     INTEGER
				MAX-ACCESS read-only
				STATUS     current
				DESCRIPTION
					"captive port id."     
				::= { dot11PortalNoAuthenticatedEntry 1 }                
                           
CaptiveInterface       		OBJECT-TYPE
				SYNTAX     DisplayString
				MAX-ACCESS read-create
				STATUS     current
				DESCRIPTION
					"Portal NoAuthenticated Switch."
				::= { dot11PortalNoAuthenticatedEntry 2 }  
				
NoAuthRowStatus	                OBJECT-TYPE
			    	SYNTAX      RowStatus
			    	MAX-ACCESS  read-create
			    	STATUS      current
			    	DESCRIPTION
			        	"This variable is used to create, modify, and/or delete a row
			        	 in this table."
			    	::= { dot11PortalNoAuthenticatedEntry 3 }							
		

dot11ConfTotalTrapGroup OBJECT IDENTIFIER ::={ dot11AcGroup 24 }

dot11ConfTotalTrapGroupTable OBJECT-TYPE
	    SYNTAX      SEQUENCE OF Dot11ConfTotalTrapGroupEntry
	    MAX-ACCESS  not-accessible
	    STATUS      current
	    DESCRIPTION
	        "Config Trap Server."
	    ::= { dot11ConfTotalTrapGroup 1 }

dot11ConfTotalTrapGroupEntry  OBJECT-TYPE
    SYNTAX      Dot11ConfTotalTrapGroupEntry
    MAX-ACCESS  not-accessible
    STATUS      current
    DESCRIPTION
        "Config Trap Server."
    INDEX { NewTrapIndex }
    ::= { dot11ConfTotalTrapGroupTable 1 }
   
Dot11ConfTotalTrapGroupEntry ::=SEQUENCE{
                NewTrapIndex      INTEGER,
                NewTrapName       DisplayString,
                NewTrapDescr      DisplayString,
		NewTrapOnOff      INTEGER
}

NewTrapIndex	                OBJECT-TYPE
				SYNTAX     INTEGER
				MAX-ACCESS read-only
				STATUS     current
				DESCRIPTION
					"NewTrapIndex."
				::= { dot11ConfTotalTrapGroupEntry 1}

NewTrapName	                OBJECT-TYPE
				SYNTAX     DisplayString
				MAX-ACCESS read-only
				STATUS     current
				DESCRIPTION
					"NewTrapName."
				::= { dot11ConfTotalTrapGroupEntry 2}
NewTrapDescr	                OBJECT-TYPE
				SYNTAX     DisplayString
				MAX-ACCESS read-write
				STATUS     current
				DESCRIPTION
					"NewTrapDescr."
				::= { dot11ConfTotalTrapGroupEntry 3 }

NewTrapOnOff	                OBJECT-TYPE
				SYNTAX     INTEGER{
                                                  on(1),
                                                  off(2)
                                                  }
				MAX-ACCESS read-write
				STATUS     current
				DESCRIPTION
					"New Trap Switch."
				::= { dot11ConfTotalTrapGroupEntry 4 }

dot11ConfigSysLogServerGroup OBJECT IDENTIFIER ::={ dot11AcGroup 25 }

dot11ConfigSysLogServerTable OBJECT-TYPE
	    SYNTAX      SEQUENCE OF Dot11ConfigSysLogServerEntry
	    MAX-ACCESS  not-accessible
	    STATUS      current
	    DESCRIPTION
	        "Config Trap Server."
	    ::= { dot11ConfigSysLogServerGroup 1 }
dot11ConfigSysLogServerEntry  OBJECT-TYPE
    SYNTAX      Dot11ConfigSysLogServerEntry
    MAX-ACCESS  not-accessible
    STATUS      current
    DESCRIPTION
        "Config Trap Server."
    INDEX { SyslogIndex }
    ::= { dot11ConfigSysLogServerTable 1 }
   
Dot11ConfigSysLogServerEntry ::=SEQUENCE{
		SyslogIndex		INTEGER,              
                SyslogServerIPPort      TAddress,		
		SyslogRowStatus		RowStatus
}
SyslogIndex	 	OBJECT-TYPE
				SYNTAX     INTEGER 
				MAX-ACCESS read-only
				STATUS     current
				DESCRIPTION
					"Syslog index."
				::= { dot11ConfigSysLogServerEntry 1 }
SyslogServerIPPort  	        OBJECT-TYPE
				SYNTAX     TAddress
				MAX-ACCESS read-create
				STATUS     current
				DESCRIPTION
					"SyslogServerIPAddr,config for IP:Port . Use MG-SOFT MIB browser and select Bits when set value . example,# 0xC0 0xA8 0xA8 0xA8 0xA8 0xA8."
				::= { dot11ConfigSysLogServerEntry 2 }

SyslogRowStatus			OBJECT-TYPE
			    	SYNTAX      RowStatus
			    	MAX-ACCESS  read-create
			    	STATUS      current
			    	DESCRIPTION
			        	"This variable is used to create, modify, and/or delete a row
			        	 in this table."
			    	::= { dot11ConfigSysLogServerEntry 3 }
			    	
dot11ConfigSyslogGlobal OBJECT IDENTIFIER ::={ dot11ConfigSysLogServerGroup 2 }

SyslogServcEnableg 	        OBJECT-TYPE
				SYNTAX     TruthValue 
				MAX-ACCESS read-write
				STATUS     current
				DESCRIPTION
					"SyslogEnable.  true 1 and  false 2"
				::= { dot11ConfigSyslogGlobal 1 }

SyslogReportLevelg              OBJECT-TYPE
				SYNTAX     INTEGER{
							Information(1),
						 	Notice(2),
						 	Warning(3),
						 	Error(4),
						 	Critical(5),
						 	Debug(6)					 
						 }
				MAX-ACCESS read-write
				STATUS     current
				DESCRIPTION
					"syslog Report Level."
				::= { dot11ConfigSyslogGlobal 2 }


dot11ConfigIpGroup OBJECT IDENTIFIER ::={ dot11AcGroup 26 }

dot11ConfigIpGroupTable OBJECT-TYPE
	    SYNTAX      SEQUENCE OF Dot11ConfigIpGroupEntry
	    MAX-ACCESS  not-accessible
	    STATUS      current
	    DESCRIPTION
	        "Shows config Ip Index."
	    ::= { dot11ConfigIpGroup 1 }
	    
dot11ConfigIpGroupEntry  OBJECT-TYPE
    SYNTAX      Dot11ConfigIpGroupEntry
    MAX-ACCESS  not-accessible
    STATUS      current
    DESCRIPTION
        "Config Ip Group."
    INDEX { Ifconfigindex }
    ::= { dot11ConfigIpGroupTable 1 }
   
Dot11ConfigIpGroupEntry ::=SEQUENCE{
                Ifconfigindex            INTEGER,
		IfconfigIpAddr	         IpAddress,
                IfconfigNetmask          IpAddress,
                ConfigIpRowStatus        RowStatus
}
Ifconfigindex	                OBJECT-TYPE
				SYNTAX     INTEGER
				MAX-ACCESS read-create
				STATUS     current
				DESCRIPTION
					"Ip Ifconfigindex."
				::= { dot11ConfigIpGroupEntry 1 }

IfconfigIpAddr                  OBJECT-TYPE
				SYNTAX     IpAddress
				MAX-ACCESS read-create
				STATUS     current
				DESCRIPTION
					"Create configIpAddr."
				::= { dot11ConfigIpGroupEntry 2 }

IfconfigNetmask                 OBJECT-TYPE
				SYNTAX     IpAddress
				MAX-ACCESS read-create
				STATUS     current
				DESCRIPTION
					"Create Netmask."
				::= { dot11ConfigIpGroupEntry 3 }

ConfigIpRowStatus	        OBJECT-TYPE
			    	SYNTAX      RowStatus
			    	MAX-ACCESS  read-create
			    	STATUS      current
			    	DESCRIPTION
			        	"This variable is used to create, modify, and/or delete a row
			        	 in this table."
			    	::= { dot11ConfigIpGroupEntry 4 }
			    		                       
dot11ConfigRadiusServerGroup OBJECT IDENTIFIER ::={ dot11AcGroup 27 }

dot11ConfigPortalRadiusAuthServerTable OBJECT-TYPE
	    SYNTAX      SEQUENCE OF Dot11ConfigPortalRadiusAuthServerEntry
	    MAX-ACCESS  not-accessible
	    STATUS      current
	    DESCRIPTION
	        "This table Config RadiusAuthServer."
	    ::= { dot11ConfigRadiusServerGroup 1 }

dot11ConfigPortalRadiusAuthServerEntry  OBJECT-TYPE
    SYNTAX      Dot11ConfigPortalRadiusAuthServerEntry
    MAX-ACCESS  not-accessible
    STATUS      current
    DESCRIPTION
        "Config RadiusAuthServer."
    INDEX { InstanceId }
    ::= { dot11ConfigPortalRadiusAuthServerTable 1 }

Dot11ConfigPortalRadiusAuthServerEntry ::=SEQUENCE{
                PortalRadiusAuthDomain                                  DisplayString,
		NewPortalAuthServerIPAdd	                        IpAddress,
		NewPortalAuthServerPort		                        INTEGER,
                NewPortalAuthServerSharedkey                            DisplayString,
                NewPortalRadiusAuthServerIPAdd                          IpAddress,
                NewPortalRadiusAuthServerPort                           INTEGER,
                NewPortalRadiusAuthServerSharedkey                      DisplayString,
                NewPortalAccServerIPAdd	                                IpAddress,
		NewPortalAccServerPort		                        INTEGER,
                NewPortalAccServerSharedkey                             DisplayString,
                NewPortalRadiusAccServerIPAdd                           IpAddress,
                NewPortalRadiusAccServerPort                            INTEGER,
                NewPortalRadiusAccServerSharedkey                       DisplayString,
                NewPortalRadiusServerRowStatus			        RowStatus
}

PortalRadiusAuthDomain	        OBJECT-TYPE
				SYNTAX  DisplayString
				MAX-ACCESS read-create
				STATUS     current
				DESCRIPTION
					"RadiusDomain."
				::= { dot11ConfigPortalRadiusAuthServerEntry 1 }

NewPortalAuthServerIPAdd	OBJECT-TYPE
				SYNTAX  IpAddress
				MAX-ACCESS read-create
				STATUS     current
				DESCRIPTION
					"NewAuthServerIPAdd."
				::= { dot11ConfigPortalRadiusAuthServerEntry 2 }
NewPortalAuthServerPort	        OBJECT-TYPE
				SYNTAX  INTEGER(1..65535)
				MAX-ACCESS read-create
				STATUS     current
				DESCRIPTION
					"NewAuthServerPort."
				::= { dot11ConfigPortalRadiusAuthServerEntry 3 }

NewPortalAuthServerSharedkey	 OBJECT-TYPE
				SYNTAX  DisplayString
				MAX-ACCESS read-create
				STATUS     current
				DESCRIPTION
					"NewAuthServerSharedkey."
				::= { dot11ConfigPortalRadiusAuthServerEntry 4 }
NewPortalRadiusAuthServerIPAdd	OBJECT-TYPE
				SYNTAX  IpAddress
				MAX-ACCESS read-create
				STATUS     current
				DESCRIPTION
					"NewRadiusAuthServerIPAdd."
				::= { dot11ConfigPortalRadiusAuthServerEntry 5 }
NewPortalRadiusAuthServerPort	OBJECT-TYPE
				SYNTAX  INTEGER(1..65535)
				MAX-ACCESS read-create
				STATUS     current
				DESCRIPTION
					"NewRadiusAuthServerPort."
				::= { dot11ConfigPortalRadiusAuthServerEntry 6 }
NewPortalRadiusAuthServerSharedkey	OBJECT-TYPE
					SYNTAX  DisplayString
					MAX-ACCESS read-create
					STATUS     current
					DESCRIPTION
						"NewRadiusAuthServerSharedkey."
					::= { dot11ConfigPortalRadiusAuthServerEntry 7 }
				
NewPortalAccServerIPAdd	        OBJECT-TYPE
				SYNTAX  IpAddress
				MAX-ACCESS read-create
				STATUS     current
				DESCRIPTION
					"NewAccServerIPAdd."
				::= { dot11ConfigPortalRadiusAuthServerEntry 8 }
NewPortalAccServerPort	        OBJECT-TYPE
				SYNTAX  INTEGER(1..65535)
				MAX-ACCESS read-create
				STATUS     current
				DESCRIPTION
					"NewAccServerPort."
				::= { dot11ConfigPortalRadiusAuthServerEntry 9 }

NewPortalAccServerSharedkey	OBJECT-TYPE
				SYNTAX  DisplayString
				MAX-ACCESS read-create
				STATUS     current
				DESCRIPTION
					"NewAccServerSharedkey."
				::= { dot11ConfigPortalRadiusAuthServerEntry 10 }
NewPortalRadiusAccServerIPAdd	OBJECT-TYPE
				SYNTAX  IpAddress
				MAX-ACCESS read-create
				STATUS     current
				DESCRIPTION
					"NewRadiusAccServerIPAdd."
				::= { dot11ConfigPortalRadiusAuthServerEntry 11 }
NewPortalRadiusAccServerPort	OBJECT-TYPE
				SYNTAX  INTEGER(1..65535)
				MAX-ACCESS read-create
				STATUS     current
				DESCRIPTION
					"NewRadiusAccServerPort."
				::= { dot11ConfigPortalRadiusAuthServerEntry 12 }
NewPortalRadiusAccServerSharedkey	OBJECT-TYPE
					SYNTAX  DisplayString
					MAX-ACCESS read-create
					STATUS     current
					DESCRIPTION
						"NewRadiusAccServerSharedkey."
					::= { dot11ConfigPortalRadiusAuthServerEntry 13 }
NewPortalRadiusServerRowStatus	OBJECT-TYPE
				SYNTAX  RowStatus
				MAX-ACCESS read-create
				STATUS     current
				DESCRIPTION
					"NewRadiusAuthServerRowStatus."
				::= { dot11ConfigPortalRadiusAuthServerEntry 14 }

dot11HansiTable OBJECT-TYPE
	    SYNTAX      SEQUENCE OF Dot11HansiEntry
	    MAX-ACCESS  not-accessible
	    STATUS      current
	    DESCRIPTION
	        "This table shows BSSID config permission information."
	    ::= { dot11AcGroup 29 }

dot11HansiEntry  OBJECT-TYPE
    SYNTAX      Dot11HansiEntry
    MAX-ACCESS  not-accessible
    STATUS      current
    DESCRIPTION
        "HANSI config  information."
    INDEX { VrrpID }
    ::= { dot11HansiTable 1 }
   
Dot11HansiEntry ::=SEQUENCE{
	VrrpID			INTEGER,
	HansiState		INTEGER,
	HansiUplinkIP          DisplayString,
	HansiDownlinkIP          DisplayString,
	HansiHblinkIP          DisplayString
}

VrrpID			OBJECT-TYPE
			SYNTAX  INTEGER
			MAX-ACCESS read-only
			STATUS     current
			DESCRIPTION
				"HANSI  ID."
			::= { dot11HansiEntry 1 }

HansiState			 	OBJECT-TYPE
					SYNTAX     INTEGER{
                                                        Back(0),
							Master(1)
							} 
					MAX-ACCESS read-write
					STATUS     current
					DESCRIPTION
				        	"HANSI config."
					::= { dot11HansiEntry 2 }
			
HansiUplinkIP		OBJECT-TYPE
			SYNTAX  DisplayString
			MAX-ACCESS read-only
			STATUS     current
			DESCRIPTION
				"HANSI up-link ip."
			::= { dot11HansiEntry 3 }
			
HansiDownlinkIP		OBJECT-TYPE
			SYNTAX  DisplayString
			MAX-ACCESS read-only
			STATUS     current
			DESCRIPTION
				"HANSI down-link ip."
			::= { dot11HansiEntry 4 }
			
HansiHblinkIP		OBJECT-TYPE
			SYNTAX  DisplayString
			MAX-ACCESS read-only
			STATUS     current
			DESCRIPTION
				"HANSI heart-blink ip."
			::= { dot11HansiEntry 5 }

--*********************************************************************************

dot11PermitBSSIDTable OBJECT-TYPE
	    SYNTAX      SEQUENCE OF Dot11PermitBSSIDEntry
	    MAX-ACCESS  not-accessible
	    STATUS      current
	    DESCRIPTION
	        "This table shows BSSID config permission information."
	    ::= { dot11AcGroup 28 }

dot11PermitBSSIDEntry  OBJECT-TYPE
    SYNTAX      Dot11PermitBSSIDEntry
    MAX-ACCESS  not-accessible
    STATUS      current
    DESCRIPTION
        "BSSID config permission information."
    INDEX { permitBSSIDID }
    ::= { dot11PermitBSSIDTable 1 }
   
Dot11PermitBSSIDEntry ::=SEQUENCE{
	permitBSSIDID		INTEGER,
	permitBSSID		PhysAddress,
	permitBSSIDRowStatus	RowStatus
}
permitBSSIDID		OBJECT-TYPE
			SYNTAX  INTEGER
			MAX-ACCESS read-only
			STATUS     current
			DESCRIPTION
				"BSSID permission ID."
			::= { dot11PermitBSSIDEntry 1 }

permitBSSID		OBJECT-TYPE
			SYNTAX  PhysAddress
			MAX-ACCESS read-write
			STATUS     current
			DESCRIPTION
				"BSSID config permission."
			::= { dot11PermitBSSIDEntry 2 }

permitBSSIDRowStatus	OBJECT-TYPE
		    	SYNTAX      RowStatus
		    	MAX-ACCESS  read-create
		    	STATUS      current
		    	DESCRIPTION
		        	"This variable is used to create, modify, and/or delete a row
		        	 in this table."
		    	::= { dot11PermitBSSIDEntry 3 }
--*********************************************************************************************

dot11APInfoByInterface OBJECT IDENTIFIER ::={ dot11AcGroup 30 }

dot11APSummaryInfoTable OBJECT-TYPE
	    SYNTAX      SEQUENCE OF Dot11APSummaryInfoEntry
	    MAX-ACCESS  not-accessible
	    STATUS      current
	    DESCRIPTION
	        "This table shows summary information by interface."
	    ::= { dot11APInfoByInterface 1 }

dot11APSummaryInfoEntry  OBJECT-TYPE
    SYNTAX      Dot11APSummaryInfoEntry
    MAX-ACCESS  not-accessible
    STATUS      current
    DESCRIPTION
        "Summary information by interface."
    INDEX { Interface }
    ::= { dot11APSummaryInfoTable 1 }
   
Dot11APSummaryInfoEntry ::=SEQUENCE{
	Interface		DisplayString,
	AccessApNum		INTEGER
}
Interface		OBJECT-TYPE
			SYNTAX  DisplayString
			MAX-ACCESS read-only
			STATUS     current
			DESCRIPTION
				"Interface name"
			::= { dot11APSummaryInfoEntry 1 }
						
AccessApNum		OBJECT-TYPE
			SYNTAX  INTEGER
			MAX-ACCESS read-only
			STATUS     current
			DESCRIPTION
				"The AP num that accessed this interface"
			::= { dot11APSummaryInfoEntry 2 }
			

--*********************************************************************************

dot11ApInfoTableByInterface OBJECT-TYPE
	    SYNTAX      SEQUENCE OF Dot11ApInfoTableByInterfaceEntry
	    MAX-ACCESS  not-accessible
	    STATUS      current
	    DESCRIPTION
	        "This table shows AP information by interface."
	    ::= { dot11APInfoByInterface 2 }

dot11ApInfoTableByInterfaceEntry  OBJECT-TYPE
    SYNTAX      Dot11ApInfoTableByInterfaceEntry
    MAX-ACCESS  not-accessible
    STATUS      current
    DESCRIPTION
        "AP information by interface."
    INDEX { Interface,
    	    wtpMAC }
    ::= { dot11ApInfoTableByInterface 1 }
   
Dot11ApInfoTableByInterfaceEntry ::=SEQUENCE{
	wtpMAC			DisplayString,
	wtpIPAddr		IpAddress,
	wtpSN			DisplayString
}						
wtpMAC			OBJECT-TYPE
			SYNTAX  DisplayString
			MAX-ACCESS read-only
			STATUS     current
			DESCRIPTION
				"AP MAC address"
			::= { dot11ApInfoTableByInterfaceEntry 1 }
			
wtpIPAddr		OBJECT-TYPE
			SYNTAX  IpAddress
			MAX-ACCESS read-only
			STATUS     current
			DESCRIPTION
				"AP IP address"
			::= { dot11ApInfoTableByInterfaceEntry 2 }	
			
wtpSN			OBJECT-TYPE
			SYNTAX  DisplayString
			MAX-ACCESS read-only
			STATUS     current
			DESCRIPTION
				"AP IP SN"
			::= { dot11ApInfoTableByInterfaceEntry 3 }		
			
		    	
--*********************************************************************************************

dot11RouteGroup OBJECT IDENTIFIER ::={ dot11AcGroup 32 }

dot11StaticRouteTable OBJECT-TYPE
	    SYNTAX      SEQUENCE OF Dot11StaticRouteEntry
	    MAX-ACCESS  not-accessible
	    STATUS      current
	    DESCRIPTION
	        "This table shows Static Router config  information."
	    ::= { dot11RouteGroup 1 }

dot11StaticRouteEntry  OBJECT-TYPE
    SYNTAX      Dot11StaticRouteEntry
    MAX-ACCESS  not-accessible
    STATUS      current
    DESCRIPTION
        "Static Router config information."
    INDEX { staticRouteIndex }
    ::= { dot11StaticRouteTable 1 }
   
Dot11StaticRouteEntry ::=SEQUENCE{
	staticRouteIndex	INTEGER,
	ipRouteStaticDest	IpAddress,
	ipRouteStaticMask	IpAddress,
	ipRouteStaticMode	INTEGER,
	ipRouteStaticSubnet	IpAddress,
	ipRouteStaticInterface	DisplayString,
	ipRouteStaticActive	INTEGER,
	ipRouteStaticMetric	INTEGER,
	ipRouteStaticRowStatus	RowStatus
}
staticRouteIndex	OBJECT-TYPE
			SYNTAX  INTEGER
			MAX-ACCESS read-only
			STATUS     current
			DESCRIPTION
				"ip route index"
			::= { dot11StaticRouteEntry 1 }
			
ipRouteStaticDest	OBJECT-TYPE
			SYNTAX  IpAddress
			MAX-ACCESS read-create
			STATUS     current
			DESCRIPTION
				"ip route decsript"
			::= { dot11StaticRouteEntry 2 }
						
ipRouteStaticMask	OBJECT-TYPE
			SYNTAX  IpAddress
			MAX-ACCESS read-create
			STATUS     current
			DESCRIPTION
				"ip route decsript"
			::= { dot11StaticRouteEntry 3 }
			
ipRouteStaticMode	OBJECT-TYPE
			SYNTAX  INTEGER{
					  network(1),
                                          interface(2),
                                          null0(3)
                                        }
			MAX-ACCESS read-create
			STATUS     current
			DESCRIPTION
				"ip route decsript"
			::= { dot11StaticRouteEntry 4 }
	
ipRouteStaticSubnet	OBJECT-TYPE
			SYNTAX  IpAddress
			MAX-ACCESS read-create
			STATUS     current
			DESCRIPTION
				"ip route Priority decsript"
			::= { dot11StaticRouteEntry 5 }
		
ipRouteStaticInterface	OBJECT-TYPE
			SYNTAX  DisplayString
			MAX-ACCESS read-create
			STATUS     current
			DESCRIPTION
				"ip route decsript"
			::= { dot11StaticRouteEntry 6 }
			
ipRouteStaticActive	OBJECT-TYPE
			SYNTAX  INTEGER{
					none(1),
					reject(2),
					blackhole(3),
					equalize(4)
				 	}
			MAX-ACCESS read-create
			STATUS     current
			DESCRIPTION
				"ip route decsript"
			::= { dot11StaticRouteEntry 7 }
			
ipRouteStaticMetric	OBJECT-TYPE
			SYNTAX  INTEGER(1..255)
			MAX-ACCESS read-create
			STATUS     current
			DESCRIPTION
				"ip route decsript"
			::= { dot11StaticRouteEntry 8 }

ipRouteStaticRowStatus	OBJECT-TYPE
			SYNTAX  RowStatus
			MAX-ACCESS read-create
			STATUS     current
			DESCRIPTION
				"ip route decsript"
			::= { dot11StaticRouteEntry 9 }

			

--*********************************************************************************

dot11AcTrap OBJECT IDENTIFIER ::={ dot11-wireless 5 }

acInnerTrap OBJECT IDENTIFIER
		::={ dot11AcTrap 0 }

acAplicationTrap OBJECT IDENTIFIER
		::={ dot11AcTrap 1 }
    
    
acTrapDescription	 			OBJECT-TYPE
				SYNTAX     	DisplayString 
				MAX-ACCESS 	not-accessible
				STATUS     	current
				DESCRIPTION
			   "This variable displays content of Trap warning  as follow:
			   sequence of warnings,
			   element of network device,
			   level of warning,
			   type of warning,
			   causes of warning (optional)	,
			   time of warning occurs,
			   status of warning,
			   title of warning,
			   content of warning"
				::= { dot11AcTrap 2 }
				
SequenceTrapDescription	 			OBJECT-TYPE
				SYNTAX     	DisplayString 
				MAX-ACCESS 	not-accessible
				STATUS     	current
				DESCRIPTION
			   "This variable shows sequences of trap"
				::= { dot11AcTrap 3 }
				
WarningTypeTrapDescription	 			OBJECT-TYPE
				SYNTAX     	DisplayString 
				MAX-ACCESS 	not-accessible
				STATUS     	current
				DESCRIPTION
			   "This variable shows the Warning Type of trap"
				::= { dot11AcTrap 4 }
				
WarninglevelTrapDescription	 			OBJECT-TYPE
				SYNTAX     	DisplayString 
				MAX-ACCESS 	not-accessible
				STATUS     	current
				DESCRIPTION
			   "This variable shows the Warning Level of trap"
				::= { dot11AcTrap 5 }
							
TimeTrapDescription	 			OBJECT-TYPE
				SYNTAX     	DisplayString 
				MAX-ACCESS 	not-accessible
				STATUS     	current
				DESCRIPTION
			   "This variable shows the times of trap"
				::= { dot11AcTrap 6 }				
			
StatusTrapDescription	 			OBJECT-TYPE
				SYNTAX     	DisplayString 
				MAX-ACCESS 	not-accessible
				STATUS     	current
				DESCRIPTION
			   "This variable shows the status of trap"
				::= { dot11AcTrap 7 }
				
TitleTrapDescription	 			OBJECT-TYPE
				SYNTAX     	DisplayString 
				MAX-ACCESS 	not-accessible
				STATUS     	current
				DESCRIPTION
			   "This variable shows the title of trap"
				::= { dot11AcTrap 8 }				
				
ContentTrapDescription	 			OBJECT-TYPE
				SYNTAX     	DisplayString 
				MAX-ACCESS 	not-accessible
				STATUS     	current
				DESCRIPTION
			   "This variable shows the content of trap"
				::= { dot11AcTrap 9 }		
ACIpTrapDescription	 			OBJECT-TYPE
				SYNTAX     	DisplayString 
				MAX-ACCESS 	not-accessible
				STATUS     	current
				DESCRIPTION
			   "This variable shows the AC ip of trap"
				::= { dot11AcTrap 10 }
ACPowerOffIndexTrapDescription	 			OBJECT-TYPE
				SYNTAX     	DisplayString 
				MAX-ACCESS 	not-accessible
				STATUS     	current
				DESCRIPTION
			   "This variable shows the index of power failed power supply of trap"
				::= { dot11AcTrap 11 }
ACInterfaceChangedStateTrapDescription	 			OBJECT-TYPE
				SYNTAX     	DisplayString 
				MAX-ACCESS 	not-accessible
				STATUS     	current
				DESCRIPTION
			   "This variable shows the AC interface IP add or del state of trap"
				::= { dot11AcTrap 12 }
				
acPowerOffIndex			OBJECT-TYPE
				SYNTAX     	DisplayString 
				MAX-ACCESS 	not-accessible
				STATUS     	current
				DESCRIPTION
			   "This variable shows the index of ac power"
				::= { dot11AcTrap 16 }	
				
InterfaceChangeState		OBJECT-TYPE
				SYNTAX     	DisplayString 
				MAX-ACCESS 	not-accessible
				STATUS     	current
				DESCRIPTION
			   "This variable shows the state of ac interface ip changed"
				::= { dot11AcTrap 17 }								

-- Trap father node
--	The following content is about child node of trap

	acSystemRebootTrap NOTIFICATION-TYPE
		OBJECTS {
				acNumAPInAC
			}
		STATUS		current
		DESCRIPTION
			"An acSystemRebootTrap Trap signifies that there has been an signal of AC-REBOOT "
	::= { acInnerTrap 1 }
	
	acDiscoveryDangerAPTrap NOTIFICATION-TYPE
		OBJECTS {
				acNumAPInAC
			}
		STATUS		current
		DESCRIPTION
			"An acDiscoveryDangerAPTrap Trap signifies that there has been an signal of AC-DISCOVERY-DANGER-AP "
	::= { acAplicationTrap 1 }
	
	acAPACTimeSynchroFailureTrap NOTIFICATION-TYPE
		OBJECTS {
				acNumAPInAC
			}
		STATUS		current
		DESCRIPTION
			"An acAPACTimeSynchroFailureTrap Trap signifies that there has been an signal of AC-AP-CLOCK-SYNC-FAILED "
	::= { acInnerTrap 2 }

	acAPACTimeSynchroFailureTrapClear NOTIFICATION-TYPE
		OBJECTS {
				acNumAPInAC
			}
		STATUS		current
		DESCRIPTION
			"An acAPACTimeSynchroFailureTrapClear Trap signifies that there has been an signal of AC-AP-CLOCK-SYNC-FAILED_CLEAR "
	::= { acInnerTrap 22 }
	
	acBoardExtractTrap NOTIFICATION-TYPE
		OBJECTS {
				acNumAPInAC
			}
		STATUS		current
		DESCRIPTION
			"An acBoardExtractTrap Trap signifies that the board have pulled out "
	::= { acInnerTrap 24 }
	
	acBoardInsertTrap NOTIFICATION-TYPE
		OBJECTS {
				acNumAPInAC
			}
		STATUS		current
		DESCRIPTION
			"An acBoardInsertTrap Trap signifies that the board have pushed in  "
	::= { acInnerTrap 25 }
	
	acPortDownTrap NOTIFICATION-TYPE
		OBJECTS {
				acNumAPInAC
			}
		STATUS		current
		DESCRIPTION
			"An acPortDownTrap Trap signifies that there has port down "
	::= { acInnerTrap 27 }
	
	acPortUpTrap NOTIFICATION-TYPE
		OBJECTS {
				acNumAPInAC
			}
		STATUS		current
		DESCRIPTION
			"An acPortUpTrap Trap signifies that  the port up "
	::= { acInnerTrap 26 }
	
	acRadiusAuthenticationServerNotReachTrap NOTIFICATION-TYPE
		OBJECTS {
				acNumAPInAC
			}
		STATUS		current
		DESCRIPTION
			"An acRadiusAuthenticationServerNotReachTrap Trap signifies that there has been an signal of AC-RADIUS-AUTH-NOT-REACH "
	::= { acAplicationTrap 2 }
	
	acRadiusAccountServerNotLinkTrap NOTIFICATION-TYPE
		OBJECTS {
				acNumAPInAC
			}
		STATUS		current
		DESCRIPTION
			"An acRadiusAccountServerNotLinkTrap Trap signifies that there has been an signal of AC-RADIUS-ACCOUNT-NOT-LINK	"
	::= { acAplicationTrap 3 }
	
	acPortalServerNotReachTrap NOTIFICATION-TYPE
		OBJECTS {
				acNumAPInAC
			}
		STATUS		current
		DESCRIPTION
			"An acPortalServerNotReachTrap Trap signifies that there has been an signal of AC-PORTAL-SERVER-NOT-REACH "
	::= { acAplicationTrap 4 }
	
	acAPLostNetTrap NOTIFICATION-TYPE
		OBJECTS {
				acNumAPInAC
			}
		STATUS		current
		DESCRIPTION
			"An acAPLostNetTrap Trap signifies that there has been an signal of AC-AP-OFF-NETWORK "
	::= { acAplicationTrap 5 }
	
	acChangedIPTrap NOTIFICATION-TYPE
		OBJECTS {
				acNumAPInAC
			}
		STATUS		current
		DESCRIPTION
			"An acChangedIPTrap Trap signifies that there has been an signal of AC-CHANGE-IP "
	::= { acInnerTrap 3 }
	
	acTurntoMasterDeviceTrap NOTIFICATION-TYPE
		OBJECTS {
				acNumAPInAC
			}
		STATUS		current
		DESCRIPTION
			"An acTurntoMasterDeviceTrap Trap signifies that there has been an signal of AC-SWITCH-MAIN-BACK "
	::= { acInnerTrap 4 }
	
	acCPUUtilizationOverThresholdTrap NOTIFICATION-TYPE
		OBJECTS {
				acNumAPInAC
			}
		STATUS		current
		DESCRIPTION
			"An acCPUUtilizationOverThresholdTrap Trap signifies that there has been an signal of AC-CPU-OVER-THRESHOLD "
	::= { acAplicationTrap 6 }
	
	acMemUtilizationOverThresholdTrap NOTIFICATION-TYPE
		OBJECTS {
				acNumAPInAC
			}
		STATUS		current
		DESCRIPTION
			"An acMemUtilizationOverThresholdTrap Trap signifies that there has been an signal of AC-MEM-OVER-THRESHOLD "
	::= { acAplicationTrap 7 }
	
	acBandwithOverThresholdTrap NOTIFICATION-TYPE
		OBJECTS {
				acNumAPInAC
			}
		STATUS		current
		DESCRIPTION
			"An acBandwithOverThresholdTrap Trap signifies that there has been an signal of AC-BANDWITH-OVER-THRESHOLD "
	::= { acAplicationTrap 8 }
	
	acLostPackRateOverThresholdTrap NOTIFICATION-TYPE
		OBJECTS {
				acNumAPInAC
			}
		STATUS		current
		DESCRIPTION
			"An acLostPackRateOverThresholdTrap Trap signifies that there has been an signal of AC-LOST-PACKET-RATE-OVER-THRESHOLD "
	::= { acAplicationTrap 9 }
	
	acMaxUsrNumOverThresholdTrap NOTIFICATION-TYPE
		OBJECTS {
				acNumAPInAC
			}
		STATUS		current
		DESCRIPTION
			"An acMaxUsrNumOverThresholdTrap Trap signifies that there has been an signal of AC-MAX-USR-NUMBER-OVER-THRESHOLD "
	::= { acAplicationTrap 10 }
	
	acDisconnectNumOverThresholdTrap NOTIFICATION-TYPE
		OBJECTS {
				acNumAPInAC
			}
		STATUS		current
		DESCRIPTION
			"An acDisconnectNumOverThresholdTrap Trap signifies that there has been an signal of AC-DISCONNECT-NUMBER-OVER-THRESHOLD "
	::= { acAplicationTrap 11 }
	
	acDropRateOverThresholdTrap NOTIFICATION-TYPE
		OBJECTS {
				acNumAPInAC
			}
		STATUS		current
		DESCRIPTION
			"An acDropRateOverThresholdTrap Trap signifies that there has been an signal of AC-DROP-RATE-OVER-THRESHOLD "
	::= { acAplicationTrap 12 }
	
	acOfflineSucRateBelowThresholdTrap NOTIFICATION-TYPE
		OBJECTS {
				acNumAPInAC
			}
		STATUS		current
		DESCRIPTION
			"An acOfflineSucRateBelowThresholdTrap Trap signifies that there has been an signal of AC-USR-OFFLINE-SUCCESS-RATE-BELOW-THRESHOLD "
	::= { acAplicationTrap 13 }
	
	acAuthSucRateBelowThresholdTrap NOTIFICATION-TYPE
		OBJECTS {
				acNumAPInAC
			}
		STATUS		current
		DESCRIPTION
			"An acAuthSucRateBelowThresholdTrap Trap signifies that there has been an signal of AC-USR-AUTHENTICATION-SUCCESS-RATE-BELOW-THRESHOLD "
	::= { acAplicationTrap 14 }

	acAveIPPoolOverThresholdTrap NOTIFICATION-TYPE
		OBJECTS {
				acNumAPInAC
			}
		STATUS		current
		DESCRIPTION
			"An acIPPoolOverThresholdTrap Trap signifies that there has been an signal of AC-AVERAGE-IP-POOL-UTILIZATION-OVER-THRESHOLD "
	::= { acAplicationTrap 15 }
	
	acMaxIPPoolOverThresholdTrap NOTIFICATION-TYPE
		OBJECTS {
				acNumAPInAC
			}
		STATUS		current
		DESCRIPTION
			"An acMaxIPPoolOverThresholdTrap Trap signifies that there has been an signal of AC-MAX-IP-POOL-UTILIZATION-OVER-THRESHOLD "
	::= { acAplicationTrap 16 }
	
	acDHCPSucRateOverThresholdTrap NOTIFICATION-TYPE
		OBJECTS {
				acNumAPInAC
			}
		STATUS		current
		DESCRIPTION
			"An acDHCPSucRateOverThresholdTrap Trap signifies that there has been an signal of AC-DHCP-SUCCESS-RATE-OVER-THRESHOLD "
	::= { acAplicationTrap 17 }
	
	acConfigurationErrorTrap NOTIFICATION-TYPE
		OBJECTS {
				acNumAPInAC
			}
		STATUS		current
		DESCRIPTION
			"An acConfigurationErrorTrap Trap signifies that there has been an signal of AC-CONFIGURE-ERROR "
	::= { acInnerTrap 5 }
	
	acSysColdStartTrap NOTIFICATION-TYPE
		OBJECTS {
				acNumAPInAC
			}
		STATUS		current
		DESCRIPTION
			"An acSysColdStartTrap Trap signifies that there has been an signal of AC-SYS-COLD-START "
	::= { acInnerTrap 6 }
	
	acHeartbeatTrap NOTIFICATION-TYPE
		OBJECTS {
				acNumAPInAC
			}
		STATUS		current
		DESCRIPTION
			"An acHeartbeatTrap Trap signifies that there has been an signal of AC-HEART-BEAT-TRAP "
	::= { acInnerTrap 7 }
	
	acPowerOffTrap NOTIFICATION-TYPE
		OBJECTS {
				acNumAPInAC
			}
		STATUS		current
		DESCRIPTION
			"An acPowerOffTrap Trap signifies that there has been an signal of AC-POWER-OFF "
	::= { acAplicationTrap 18 }
	
	acPowerOffRecovTrap NOTIFICATION-TYPE
		OBJECTS {
				acNumAPInAC
			}
		STATUS		current
		DESCRIPTION
			"An acPowerOffRecovTrap Trap signifies that there has been an signal of AC-POWER-OFF-RECOVER "
	::= { acAplicationTrap 19 }
	
	acCPUusageTooHighRecovTrap NOTIFICATION-TYPE
		OBJECTS {
				acNumAPInAC
			}
		STATUS		current
		DESCRIPTION
			"An acCPUusageTooHighRecovTrap Trap signifies that there has been an signal of AC-CPU-USAGE-TOO-HIGH-CLEAR "
	::= { acAplicationTrap 20 }
	
	acMemUsageTooHighRecovTrap NOTIFICATION-TYPE
		OBJECTS {
				acNumAPInAC
			}
		STATUS		current
		DESCRIPTION
			"An acMemUsageTooHighRecovTrap Trap signifies that there has been an signal of AC-MEM-USAGE-TOO-HIGH-CLEAR "
	::= { acAplicationTrap 21 }
	
	acTemperTooHighTrap NOTIFICATION-TYPE
		OBJECTS {
				acNumAPInAC
			}
		STATUS		current
		DESCRIPTION
			"An acTemperTooHighRecovTrap Trap signifies that there has been an signal of AC-TEMPER-TOO-HIGH "
	::= { acAplicationTrap 22 }
	
	acTemperTooHighRecovTrap NOTIFICATION-TYPE
		OBJECTS {
				acNumAPInAC
			}
		STATUS		current
		DESCRIPTION
			"An acTemperTooHighRecovTrap Trap signifies that there has been an signal of AC-TEMPER-TOO-HIGH-CLEAR "
	::= { acAplicationTrap 23 }
	
	acDHCPAddressExhaustTrap NOTIFICATION-TYPE
		OBJECTS {
				acNumAPInAC
			}
		STATUS		current
		DESCRIPTION
			"An acDHCPAddressExhaustTrap Trap signifies that there has been an signal of AC-DHCP-ADDRESS-EXHAUSTED "
	::= { acAplicationTrap 24 }
	
	acDHCPAddressExhaustRecovTrap NOTIFICATION-TYPE
		OBJECTS {
				acNumAPInAC
			}
		STATUS		current
		DESCRIPTION
			"An acDHCPAddressExhaustRecovTrap Trap signifies that there has been an signal of AC-DHCP-ADDRESS-EXHAUSTED-CLEAR "
	::= { acAplicationTrap 25 }
	
	acRadiusAuthServerAvailableTrap NOTIFICATION-TYPE
		OBJECTS {
				acNumAPInAC
			}
		STATUS		current
		DESCRIPTION
			"An acRadiusAuthServerAvailableTrap Trap signifies that there has been an signal of AC-RADIUS-AUTH-SERVER-NOT-TATCH-CLEAR "
	::= { acAplicationTrap 26 }
	
	acRadiusAccServerAvailableTrap NOTIFICATION-TYPE
		OBJECTS {
				acNumAPInAC
			}
		STATUS		current
		DESCRIPTION
			"An acRadiusAccServerAvailableTrap Trap signifies that there has been an signal of AC-RADIUS-ACCOUT-SERVER-NOT-TATCH-CLEAR "
	::= { acAplicationTrap 27 }
	
	acRorterServerAvailableTrap NOTIFICATION-TYPE
		OBJECTS {
				acNumAPInAC
			}
		STATUS		current
		DESCRIPTION
			"An acRorterServerAvailableTrap Trap signifies that there has been an signal of AC-PORTER-SERVER-NOT-TATCH-CLEAR "
	::= { acAplicationTrap 28 }
	
	acFindSynAttackTrap NOTIFICATION-TYPE
		OBJECTS {
				acNumAPInAC
			}
		STATUS		current
		DESCRIPTION
			"An acFindSynAttackTrap Trap signifies that there has been an signal of AC-FIND-SYN-ATTACK "
	::= { acAplicationTrap 29 }
	
	acMaxUsrNumOverThresholdTrapClear NOTIFICATION-TYPE
		OBJECTS {
				acNumAPInAC
			}
		STATUS		current
		DESCRIPTION
			"An acMaxUsrNumOverThresholdTrapClear Trap signifies that there has been an signal of AC-MAX-USR-NUMBER-OVER-THRESHOLD-CLEAR "
	::= { acAplicationTrap 30 }
	
	acHeartTimePackageTrap NOTIFICATION-TYPE
		OBJECTS {
				acNumAPInAC
			}
		STATUS		current
		DESCRIPTION
			"An acHeartTimePackageTrap Trap signifies that there has been an signal of AC-SEND_PACKAGE_IN_CIRCLE "
	::= { acAplicationTrap 50 }


END
