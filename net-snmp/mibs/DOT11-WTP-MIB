DOT11-WTP-MIB DEFINITIONS ::= BEGIN
IMPORTS

	dot11-wireless,PhysAddress 
			FROM DOT11-GROUP-SMI
--   	
	TEXTUAL-CONVENTION 
--   	NOTIFICATION-GROUP, 
--	OBJECT-GROUP, 
--	MODULE-COMPLIANCE
       			FROM SNMPv2-CONF
	TruthValue,
	DisplayString
			FROM SNMPv2-TC
   	MODULE-IDENTITY, 
	OBJECT-TYPE,
	NOTIFICATION-TYPE,
   	Integer32, 
--	Unsigned32, 
	Counter32,
	TimeTicks,
	enterprises
       			FROM SNMPv2-SMI;
	InetAddressIPv6 ::= TEXTUAL-CONVENTION
	DISPLAY-HINT "2x:"
     	STATUS       current
     	DESCRIPTION "This data type is used to model IPv6 addresses. This is a binary string of 16 octets in networkbyte-order."
	SYNTAX       OCTET STRING (SIZE (16))

dot11WtpGroup MODULE-IDENTITY
    LAST-UPDATED "201311280000Z"        -- Nov 28th, 2013
    ORGANIZATION " AuteLan Network Management Working Group
                  http://www.autelan.com"
    CONTACT-INFO
        "General Discussion: support@AuteLan.com
         To Subscribe: http://www.autelan.com

         Liu Tao
         AuteLan Technology Ltd.,NO.1 Agricultural University Sourth Street,Haidian
         District,Beijing,China(100084)
         Email:  liutao@autelan.com

         Wang Peng
         AuteLan Technology Ltd.,NO.1 Agricultural University Sourth Street,Haidian
         District,Beijing,China(100084)
         Email: wangpeng@autelan.com

	 Tang Siqi
         AuteLan Technology Ltd.,NO.1 Agricultural University Sourth Street,Haidian
         District,Beijing,China(100084)
         Email: tangsq@autelan.com"
   
    DESCRIPTION
        "Copyright (C) 2009 The Internet Society.  This version of
         the MIB module is part of RFC xxx; see the RFC itself
         for full legal notices.

         This MIB module contains managed object definitions for
         the AuteLan Protocol."
    REVISION    "201311280000Z"
    DESCRIPTION
        "Initial version published as RFC xxx,
	wtp means ACCESS POINT(AP)."
         ::= { 	dot11-wireless 1 }
         

Dot11BaseWtpIdTC ::= TEXTUAL-CONVENTION
                	--DISPLAY-HINT "128a"
    			STATUS      current
			DESCRIPTION
			      "Represents an unique identifier of a WTP instance.
			       As usual."
			SYNTAX     DisplayString
-- OCTET STRING(SIZE(128))

--fist path

wtpGeneralInfo 		OBJECT IDENTIFIER::={ dot11WtpGroup 1 }
wtpStats 		OBJECT IDENTIFIER::={ dot11WtpGroup 2 }
wtpInterface		OBJECT IDENTIFIER::={ dot11WtpGroup 3 }
wtpRadio		OBJECT IDENTIFIER::={ dot11WtpGroup 4 }
wtpWlan 		OBJECT IDENTIFIER::={ dot11WtpGroup 5 }
wtpLink 		OBJECT IDENTIFIER::={ dot11WtpGroup 6 }
wtpBaseWtps 		OBJECT IDENTIFIER::={ dot11WtpGroup 7 }
wtpStation 		OBJECT IDENTIFIER::={ dot11WtpGroup 8 }
wtpSecurity 		OBJECT IDENTIFIER::={ dot11WtpGroup 9 }
wtpWAPI	 		OBJECT IDENTIFIER::={ dot11WtpGroup 10 }
wtpRogue		OBJECT IDENTIFIER::={ dot11WtpGroup 11 }
wtpSwitch		OBJECT IDENTIFIER::={ dot11WtpGroup 12 }
widStatistics		OBJECT IDENTIFIER::={ dot11WtpGroup 13 }
wtpIDIndex              OBJECT IDENTIFIER::={ dot11WtpGroup 14 }
wtpNeighbor		OBJECT IDENTIFIER::={ dot11WtpGroup 15 }
wlanData                OBJECT IDENTIFIER::={ dot11WtpGroup 16 }
wlanPortal              OBJECT IDENTIFIER::={ dot11WtpGroup 17 }

--Trap
dot11WtpTrap OBJECT IDENTIFIER
		::={ dot11-wireless 4 }
		
wtpIpv6Info              OBJECT IDENTIFIER::={ dot11WtpGroup 18 }

wtpIpv6Prefix	 			OBJECT-TYPE
					SYNTAX     	DisplayString 
					MAX-ACCESS 	read-only
					STATUS     	current
					DESCRIPTION
				        	"AP IPv6 address prefix."
					::= { wtpIpv6Info 1 }

wtpIpv6Type	 			OBJECT-TYPE
					SYNTAX     	DisplayString 
					MAX-ACCESS 	read-only
					STATUS     	current
					DESCRIPTION
				        	"AP IPv6 address type."
					::= { wtpIpv6Info 2 }
					
dot11WtpInfoTable OBJECT-TYPE
    SYNTAX      SEQUENCE OF Dot11WtpInfoEntry
    MAX-ACCESS  not-accessible
    STATUS      current
    DESCRIPTION
        "This table shows the device's information."
    ::= { wtpGeneralInfo 1 }

dot11WtpInfoEntry  OBJECT-TYPE
    SYNTAX      Dot11WtpInfoEntry
    MAX-ACCESS  not-accessible
    STATUS      current
    DESCRIPTION
        "Device information."
    INDEX { wtpMacAddr }
    ::= { dot11WtpInfoTable 1 }
   
Dot11WtpInfoEntry ::=SEQUENCE{
	wtpMacAddr				Dot11BaseWtpIdTC,
	wtpDevName				DisplayString,
	wtpPosInfo				DisplayString,
	wtpProduct				DisplayString,
	wtpDevTypeNum				DisplayString,
	wtpSoftVersionInfo			DisplayString,
	wtpUpTime				TimeTicks,
	wtpOnlineTime				TimeTicks,
	wtpSysSoftName				OCTET STRING,
	wtpSysHWVersion				DisplayString,
	wtpSN					DisplayString,
	wtpSysSoftProductor			DisplayString,
	wtpDomain				DisplayString,
	wtpSysRestart				INTEGER,
	wtpSysReset				INTEGER,
	wtpColdReboot				INTEGER,
	wtplongitude				DisplayString,
	wtplatitude				DisplayString,
	wtpPowerType				DisplayString,
	wtpManufactureDate			DisplayString,
	wtpForwardMode				INTEGER,
	wtpCodeVersionInfo			DisplayString

}

wtpMacAddr 				OBJECT-TYPE
					SYNTAX      	Dot11BaseWtpIdTC
					MAX-ACCESS  	read-only
					STATUS      	current
					DESCRIPTION
					      "AP mac."
					::= { dot11WtpInfoEntry 1 }

wtpDevName	 			OBJECT-TYPE
					SYNTAX     	DisplayString
					MAX-ACCESS 	read-write
					STATUS     	current
					DESCRIPTION
				        	"AP device's name."
					::= { dot11WtpInfoEntry 2 }

wtpPosInfo	 			OBJECT-TYPE
					SYNTAX     DisplayString(SIZE(1..255))
					MAX-ACCESS read-write
					STATUS     current
					DESCRIPTION
				        	"The location of the AP device."
					::= { dot11WtpInfoEntry 3 }

wtpProduct	 			OBJECT-TYPE
					SYNTAX     DisplayString 
					MAX-ACCESS read-only
					STATUS     current
					DESCRIPTION
				        	"The AP device's manufacturer."
					::= { dot11WtpInfoEntry 4 }

wtpDevTypeNum	 			OBJECT-TYPE
					SYNTAX     DisplayString 
					MAX-ACCESS read-only
					STATUS     current
					DESCRIPTION
				        	"The AP device type number."
					::= { dot11WtpInfoEntry 5 }

wtpSoftVersionInfo	 			OBJECT-TYPE
					SYNTAX     DisplayString 
					MAX-ACCESS read-only
					STATUS     current
					DESCRIPTION
				        	"The software version of the AP device."
					::= { dot11WtpInfoEntry 6 }

wtpUpTime	 			OBJECT-TYPE
					SYNTAX     TimeTicks 
					MAX-ACCESS read-only
					STATUS     current
					DESCRIPTION
				        	"The runtime of AP."
					::= { dot11WtpInfoEntry 7 }

wtpOnlineTime	 			OBJECT-TYPE
					SYNTAX     TimeTicks 
					MAX-ACCESS read-only
					STATUS     current
					DESCRIPTION
				        	"Length of time on-line."
					::= { dot11WtpInfoEntry 8 }

wtpSysSoftName		 		OBJECT-TYPE
					SYNTAX     OCTET STRING 
					MAX-ACCESS read-only
					STATUS     current
					DESCRIPTION
				        	"The system software name or type."
					::= { dot11WtpInfoEntry 9 }

wtpSysHWVersion		 	OBJECT-TYPE
					SYNTAX     DisplayString 
					MAX-ACCESS read-only
					STATUS     current
					DESCRIPTION
				        	"The system hardware version number."
					::= { dot11WtpInfoEntry 10 }

wtpSN		 		OBJECT-TYPE
					SYNTAX     DisplayString 
					MAX-ACCESS read-only
					STATUS     current
					DESCRIPTION
				        	"The system serial-number."
					::= { dot11WtpInfoEntry 11 }

wtpSysSoftProductor		 	OBJECT-TYPE
					SYNTAX     DisplayString 
					MAX-ACCESS read-only
					STATUS     current
					DESCRIPTION
				        	"The system software manufacturer."
					::= { dot11WtpInfoEntry 12 }

wtpDomain			 	OBJECT-TYPE
					SYNTAX     DisplayString 
					MAX-ACCESS read-only
					STATUS     current
					DESCRIPTION
				        	"The country or district the device support."
					::= { dot11WtpInfoEntry 13 }

wtpSysRestart			 	OBJECT-TYPE
					SYNTAX     INTEGER{
							Normal(1),
                                                        Restart(2)
							} 
					MAX-ACCESS read-write
					STATUS     current
					DESCRIPTION
				        	"Restart AP."
					::= { dot11WtpInfoEntry 14 }

wtpSysReset			 	OBJECT-TYPE
					SYNTAX     INTEGER{
                                                        Normal(1),
							Reset(2)
							} 
					MAX-ACCESS read-write
					STATUS     current
					DESCRIPTION
				        	"Reset AP."
					::= { dot11WtpInfoEntry 15 }


wtpColdReboot				OBJECT-TYPE
					SYNTAX		INTEGER{
								reboot(1)
								}
					MAX-ACCESS 	read-write
					STATUS		current
					DESCRIPTION
						"AP cold reboot"
					::={  dot11WtpInfoEntry 16 }

wtplongitude	 			OBJECT-TYPE
					SYNTAX     	DisplayString
					MAX-ACCESS 	read-write
					STATUS     	current
					DESCRIPTION
				        	"AP device's longitude."
					::= { dot11WtpInfoEntry 17 }

wtplatitude	 			OBJECT-TYPE
					SYNTAX     	DisplayString
					MAX-ACCESS 	read-write
					STATUS     	current
					DESCRIPTION
				        	"AP device's latitude."
					::= { dot11WtpInfoEntry 18 }

wtpPowerType	 			OBJECT-TYPE
					SYNTAX     	DisplayString
					MAX-ACCESS 	read-only
					STATUS     	current
					DESCRIPTION
				        	"AP device's PowerType."
					::= { dot11WtpInfoEntry 19 }

wtpManufactureDate	 			OBJECT-TYPE
					SYNTAX     	DisplayString
					MAX-ACCESS 	read-only
					STATUS     	current
					DESCRIPTION
				        	"AP device's ManufactureDate."
					::= { dot11WtpInfoEntry 20 }

wtpForwardMode	 			OBJECT-TYPE
					SYNTAX     	INTEGER{
								Fat(0),
                                                        	Thin(1),
                                                        	Unknown(2)
								} 
					MAX-ACCESS 	read-only
					STATUS     	current
					DESCRIPTION
				        	"AP device's ForwardMode."
					::= { dot11WtpInfoEntry 21 }
					
wtpCodeVersionInfo	 			OBJECT-TYPE
					SYNTAX     DisplayString 
					MAX-ACCESS read-only
					STATUS     current
					DESCRIPTION
				        	"The code version of the AP device."
					::= { dot11WtpInfoEntry 22 }


dot11WtpSignalTable OBJECT-TYPE
    SYNTAX      SEQUENCE OF Dot11WtpSignalEntry
    MAX-ACCESS  not-accessible
    STATUS      current
    DESCRIPTION
        "This table include signal information."
    ::= { wtpStats 1 }

dot11WtpSignalEntry  OBJECT-TYPE
    SYNTAX      Dot11WtpSignalEntry
    MAX-ACCESS  not-accessible
    STATUS      current
    DESCRIPTION
        "Signal information."
    INDEX { wtpMacAddr }
    ::= { dot11WtpSignalTable 1 }

Dot11WtpSignalEntry ::=SEQUENCE{
	wtpAllSignalPack			Counter32,
	wtpRxSignalPack				Counter32,
	wtpTxSignalPack				Counter32,
	wtpDataType				DisplayString
}

wtpAllSignalPack		 	OBJECT-TYPE
					SYNTAX     Counter32 
					MAX-ACCESS read-only
					STATUS     current
					DESCRIPTION
				        	"The total number of packages in the signaling channel of the runtime.(Update time less than 2 seconds)"
					::= { dot11WtpSignalEntry 1 }

wtpRxSignalPack		 		OBJECT-TYPE
					SYNTAX     Counter32 
					MAX-ACCESS read-only
					STATUS     current
					DESCRIPTION
				        	"The number of signal packages which receiving during the runtime.(Update time less than 2 seconds)"
					::= { dot11WtpSignalEntry 2 }

wtpTxSignalPack		 		OBJECT-TYPE
					SYNTAX     Counter32 
					MAX-ACCESS read-only
					STATUS     current
					DESCRIPTION
				        	"The number of signaling packages which sending during the runtime.(Update time less than 2 seconds)"
					::= { dot11WtpSignalEntry 3 }
wtpDataType				OBJECT-TYPE
					SYNTAX     DisplayString 
					MAX-ACCESS read-only
					STATUS     current
					DESCRIPTION
				        	"The signal data type."
					::= { dot11WtpSignalEntry 4 }
dot11WtpEthPortTable OBJECT-TYPE
    SYNTAX      SEQUENCE OF Dot11WtpEthPortEntry
    MAX-ACCESS  not-accessible
    STATUS      current
    DESCRIPTION
        "This table include port information."
    ::= { wtpStats 2 }

dot11WtpEthPortEntry  OBJECT-TYPE
    SYNTAX      Dot11WtpEthPortEntry
    MAX-ACCESS  not-accessible
    STATUS      current
    DESCRIPTION
        "Port information."
    INDEX { wtpMacAddr }
    ::= { dot11WtpEthPortTable 1 }

Dot11WtpEthPortEntry ::=SEQUENCE{
	wtpWirelessUpPortRate			Counter32,
	wtpWirelessDownPortRate			Counter32,
	wtpWirelessUpPortUDTimes		INTEGER,
	wtpWirelessDownPortUDTimes		INTEGER,
	wtpUplinkDataThroughput			Counter32,
	wtpDownlinkDataThroughput		Counter32,
	wtpPhyInterMnt				INTEGER,
	wtpWirelessBandwidthUsage               DisplayString,
	wtpWirelessPortRxRate			Counter32,
	wtpWirelessPortTxRate			Counter32
}
wtpWirelessUpPortRate		 	OBJECT-TYPE
					SYNTAX     Counter32 
					MAX-ACCESS read-only
					STATUS     current
					DESCRIPTION
				        	"Wireless uplink port traffic during the sample time.(Unit Byte/s)"
					::= { dot11WtpEthPortEntry 1 }

wtpWirelessDownPortRate		 	OBJECT-TYPE
					SYNTAX     Counter32 
					MAX-ACCESS read-only
					STATUS     current
					DESCRIPTION
				        	"Wireless downlink port traffic during the sample time.(Unit Byte/s)"
					::= { dot11WtpEthPortEntry 2 }

wtpWirelessUpPortUDTimes	 	OBJECT-TYPE
					SYNTAX     	INTEGER 
					UNITS		"Times"
					MAX-ACCESS 	read-only
					STATUS     	current
					DESCRIPTION
				        	"Uplink wireless port updown times.(Times)"
					::= { dot11WtpEthPortEntry 3 }

wtpWirelessDownPortUDTimes	 	OBJECT-TYPE
					SYNTAX     	INTEGER 
					UNITS		"Times"
					MAX-ACCESS 	read-only
					STATUS     	current
					DESCRIPTION
				        	"Downlink wireless port updown times.(Times)"
					::= { dot11WtpEthPortEntry 4 }

wtpUplinkDataThroughput 		OBJECT-TYPE
					SYNTAX     	Counter32 
					UNITS		"kbps"
					MAX-ACCESS 	read-only
					STATUS     	current
					DESCRIPTION
				        	"The uplink port traffic of AP ethernet designated by AC.(bps)"
					::= { dot11WtpEthPortEntry 5 }

wtpDownlinkDataThroughput 		OBJECT-TYPE
					SYNTAX     	Counter32 
					UNITS		"kbps"
					MAX-ACCESS 	read-only
					STATUS     	current
					DESCRIPTION
				        	"The downlink port traffic of AP ethernet designated by AC.(bps)."
					::= { dot11WtpEthPortEntry 6 }

wtpPhyInterMnt			 	OBJECT-TYPE
					SYNTAX     INTEGER 
					MAX-ACCESS read-only
					STATUS     current
					DESCRIPTION
				        	"The total number of physical interface in the system."
					::= { dot11WtpEthPortEntry 7 }
					
wtpWirelessBandwidthUsage 		OBJECT-TYPE
					SYNTAX     	DisplayString 
					MAX-ACCESS 	read-only
					STATUS     	current
					DESCRIPTION
				        	"The wireless bandwidth usage."
					::= { dot11WtpEthPortEntry 8 }					

wtpWirelessPortRxRate		 	OBJECT-TYPE
					SYNTAX     Counter32 
					MAX-ACCESS read-only
					STATUS     current
					DESCRIPTION
				        	"Wireless uplink port traffic during the sample time.(Unit Kbyte/s)"
					::= { dot11WtpEthPortEntry 9 }

wtpWirelessPortTxRate		 	OBJECT-TYPE
					SYNTAX     Counter32 
					MAX-ACCESS read-only
					STATUS     current
					DESCRIPTION
				        	"Wireless downlink port traffic during the sample time.(Unit Kbyte/s)"
					::= { dot11WtpEthPortEntry 10 }
					
dot11WtpDataPktsTable OBJECT-TYPE
    SYNTAX      SEQUENCE OF Dot11WtpDataPktsEntry
    MAX-ACCESS  not-accessible
    STATUS      current
    DESCRIPTION
        "This table include data packets information."
    ::= { wtpStats 3 }

dot11WtpDataPktsEntry  OBJECT-TYPE
    SYNTAX      Dot11WtpDataPktsEntry
    MAX-ACCESS  not-accessible
    STATUS      current
    DESCRIPTION
        "Packets information."
    INDEX { wtpMacAddr }
    ::= { dot11WtpDataPktsTable 1 }

Dot11WtpDataPktsEntry ::=SEQUENCE{
	wtpWirelessMacRxAllByte			Counter64,
	wtpWirelessMacTxAllByte			Counter64,
	wtpWirelessMacRxPack			Counter32,
	wtpWirelessMacRxErrPack			Counter32,
	wtpWiredMacRxAllByte			Counter64,
	wtpWiredMacTxAllByte			Counter64,
	wtpWiredMacRxErrPack			Counter32,
	wtpWirelessMacTxDropPkts		Counter32,
	wtpWirelessMacTxPack			Counter32,
	wtpWirelessMacTxErrPack			Counter32,
	wtpWirelessMacRxRightPack		Counter32,
	wtpWirelessMacTxRightPack		Counter32,
	wtpWiredMacRxPack			Counter32,
	wtpWiredMacRxRightPack			Counter32,
	wtpWiredMacTxPack			Counter32,
	wtpWiredMacTxErrPack 			Counter32,
	wtpWiredMacTxRightPack			Counter32,
        wtpWirelessradioRecvBytes               Counter32,
        wtpWirelesscoreRecvBytes                Counter64,
        wtpWirelessRxFlowByte			Counter64,
	wtpWirelessTxFlowByte			Counter64  
}
wtpWirelessMacRxAllByte 		OBJECT-TYPE
					SYNTAX     	Counter64 
					MAX-ACCESS 	read-only
					STATUS     	current
					DESCRIPTION
				        	"On the wireless side,the received right bytes of package in the MAC level."
					::= { dot11WtpDataPktsEntry 1 }
wtpWirelessMacTxAllByte 		OBJECT-TYPE
					SYNTAX     	Counter64 
					MAX-ACCESS 	read-only
					STATUS     	current
					DESCRIPTION
				        	"On the wireless side,all the sent bytes of package in the MAC level.(KB)"
					::= { dot11WtpDataPktsEntry 2 }
wtpWirelessMacRxPack 			OBJECT-TYPE
					SYNTAX     	Counter32 
					MAX-ACCESS 	read-only
					STATUS     	current
					DESCRIPTION
				        	"On the wireless side,all the received packages in the MAC level."
					::= { dot11WtpDataPktsEntry 3 }
wtpWirelessMacRxErrPack 			OBJECT-TYPE
					SYNTAX     	Counter32 
					MAX-ACCESS 	read-only
					STATUS     	current
					DESCRIPTION
				        	"On the wireless side,the received error package in the MAC level."
					::= { dot11WtpDataPktsEntry 4 }

wtpWiredMacRxAllByte 			OBJECT-TYPE
					SYNTAX     	Counter64 
					MAX-ACCESS 	read-only
					STATUS     	current
					DESCRIPTION
				        	"On the wire side,the received right bytes of package in the MAC level.(KB)"
					::= { dot11WtpDataPktsEntry 5 }
wtpWiredMacTxAllByte 			OBJECT-TYPE
					SYNTAX     	Counter64 
					MAX-ACCESS 	read-only
					STATUS     	current
					DESCRIPTION
				        	"On the wire side,all the sent bytes of package in the MAC level.(KB)"
					::= { dot11WtpDataPktsEntry 6 }
wtpWiredMacRxErrPack			OBJECT-TYPE
					SYNTAX     	Counter32 
					MAX-ACCESS 	read-only
					STATUS     	current
					DESCRIPTION
				        	"On the wire side,the received error number of package in the MAC level."
					::= { dot11WtpDataPktsEntry 7 }

wtpWirelessMacTxDropPkts		OBJECT-TYPE
					SYNTAX     	Counter32 
					MAX-ACCESS 	read-only
					STATUS     	current
					DESCRIPTION
				        	"On the Wireless side,all the send drop package in the MAC level."
					::= { dot11WtpDataPktsEntry 8 }
					
wtpWirelessMacTxPack 			OBJECT-TYPE
					SYNTAX     	Counter32 
					MAX-ACCESS 	read-only
					STATUS     	current
					DESCRIPTION
				        	"On the wireless side,the send  number of package in the MAC level."
					::= { dot11WtpDataPktsEntry 9 }
wtpWirelessMacTxErrPack			OBJECT-TYPE
					SYNTAX     	Counter32 
					MAX-ACCESS 	read-only
					STATUS     	current
					DESCRIPTION
				        	"On the wireless side,the send error package in the MAC level."
					::= { dot11WtpDataPktsEntry 10 }
wtpWirelessMacRxRightPack		OBJECT-TYPE
					SYNTAX     	Counter32 
					MAX-ACCESS 	read-only
					STATUS     	current
					DESCRIPTION
				        	"On the wireless side,the received right package in the MAC level."
					::= { dot11WtpDataPktsEntry 11 }
wtpWirelessMacTxRightPack		OBJECT-TYPE
					SYNTAX     	Counter32 
					MAX-ACCESS 	read-only
					STATUS     	current
					DESCRIPTION
				        	"On the wireless side,the send right package in the MAC level."
					::= { dot11WtpDataPktsEntry 12 }
wtpWiredMacRxPack			OBJECT-TYPE
					SYNTAX     	Counter32 
					MAX-ACCESS 	read-only
					STATUS     	current
					DESCRIPTION
				        	"On the wire side,the received  package in the MAC level."
					::= { dot11WtpDataPktsEntry 13 }
wtpWiredMacRxRightPack			OBJECT-TYPE
					SYNTAX     	Counter32 
					MAX-ACCESS 	read-only
					STATUS     	current
					DESCRIPTION
				        	"On the wire side,the send right package in the MAC level."
					::= { dot11WtpDataPktsEntry 14 }
wtpWiredMacTxPack			OBJECT-TYPE
					SYNTAX     	Counter32 
					MAX-ACCESS 	read-only
					STATUS     	current
					DESCRIPTION
				        	"On the wire side,the send  package in the MAC level."
					::= { dot11WtpDataPktsEntry 15}
wtpWiredMacTxErrPack 			OBJECT-TYPE
					SYNTAX     	Counter32 
					MAX-ACCESS 	read-only
					STATUS     	current
					DESCRIPTION
				        	"On the wire side,the send error package in the MAC level."
					::= { dot11WtpDataPktsEntry 16 }
wtpWiredMacTxRightPack			OBJECT-TYPE
					SYNTAX     	Counter32 
					MAX-ACCESS 	read-only
					STATUS     	current
					DESCRIPTION
				        	"On the wire side,the send right package in the MAC level."
					::= { dot11WtpDataPktsEntry 17 }
wtpWirelessradioRecvBytes		OBJECT-TYPE
					SYNTAX     	Counter32 
					MAX-ACCESS 	read-only
					STATUS     	current
					DESCRIPTION
				        	"On the wireless side,the send right package in the MAC level."
					::= { dot11WtpDataPktsEntry 18 }

wtpWirelesscoreRecvBytes		OBJECT-TYPE
					SYNTAX     	Counter64 
					MAX-ACCESS 	read-only
					STATUS     	current
					DESCRIPTION
				        	"On the wireless side,the send right package in the MAC level."
					::= { dot11WtpDataPktsEntry 19 }
						
wtpWirelessRxFlowByte 			OBJECT-TYPE
					SYNTAX     	Counter64 
					MAX-ACCESS 	read-only
					STATUS     	current
					DESCRIPTION
				        	"The received bytes on the wireless side,the data is not cleared if AP restart."
					::= { dot11WtpDataPktsEntry 20 }
wtpWirelessTxFlowByte 			OBJECT-TYPE
					SYNTAX     	Counter64 
					MAX-ACCESS 	read-only
					STATUS     	current
					DESCRIPTION
				        	"The sent bytes on the wireless side,the data is not cleared if AP restart."
					::= { dot11WtpDataPktsEntry 21 }					


dot11WtpStatsTable OBJECT-TYPE
    SYNTAX      SEQUENCE OF Dot11WtpStatsEntry
    MAX-ACCESS  not-accessible
    STATUS      current
    DESCRIPTION
        "This table include status information."
    ::= { wtpStats 4 }

dot11WtpStatsEntry  OBJECT-TYPE
    SYNTAX      Dot11WtpStatsEntry
    MAX-ACCESS  not-accessible
    STATUS      current
    DESCRIPTION
        "Status information."
    INDEX { wtpMacAddr }
    ::= { dot11WtpStatsTable 1 }
Dot11WtpStatsEntry ::=SEQUENCE{
	wtpAllowConUsrMnt			INTEGER,
	wtpMountConUsrTimes			Counter32,
	wtpMountConFailTimes			Counter32,
	wtpMountConReasTimes			Counter32,
	wtpSupportSSID				DisplayString,
	wtpOnlineUsrNum				INTEGER,
	wtpUsrRequestConnect			Counter32,
	wtpResponseUsrConnect			Counter32,
	wtpLoginSuccNum				Counter32,
	wtpLessResourceRefuseNewUsrMount	Counter32,
	wtpStatsDisassociated			Counter32,
	wtpUsrWirelessResoUseRate		DisplayString,
	wtpSSIDNum				INTEGER,
	wtpAllStaAssTime			TimeTicks,
	wtpConfigBSSIDNum			INTEGER,
	wtpInterfaceNum				Integer32,
	wtpAssocSuccessTimes			Counter32,
	wtpRSSILowAssocFailTimes		Counter32,
	wtpHeartBeatAvgTimeDelay		Integer32,
	wtpEchoReqCnt				Counter32,
	wtpEchoRespLossCnt			Counter32,
	wtpResponseUsrConnectSuccess		Counter32,
	wtpResponseUsrConnectFail		Counter32,
	wtpMountConReasFailTimes		Counter32
}
wtpAllowConUsrMnt			OBJECT-TYPE
					SYNTAX     INTEGER 
					MAX-ACCESS read-write
					STATUS     current
					DESCRIPTION
				        	"The total number of user allowed to switch-in. set 0-64"
					::= { dot11WtpStatsEntry 1 }

wtpMountConUsrTimes		 	OBJECT-TYPE
					SYNTAX     	Counter32 
					UNITS		"Times"
					MAX-ACCESS 	read-only
					STATUS     	current
					DESCRIPTION
				        	"The number of users(802.11b/g) associated.(Times)"
					::= { dot11WtpStatsEntry 2 }

wtpMountConFailTimes		 	OBJECT-TYPE
					SYNTAX     	Counter32
					UNITS 		"Times"
					MAX-ACCESS 	read-only
					STATUS     	current
					DESCRIPTION
				        	"The number of 802.11b/g failed link.(Times)"
					::= { dot11WtpStatsEntry 3 }

wtpMountConReasTimes		 	OBJECT-TYPE
					SYNTAX     Counter32 
					MAX-ACCESS read-only
					STATUS     current
					DESCRIPTION
				        	"The total number of current reassociate(802.11b/g).(Times)"
					::= { dot11WtpStatsEntry 4 }

wtpSupportSSID				OBJECT-TYPE
					SYNTAX     DisplayString 
					MAX-ACCESS read-only
					STATUS     current
					DESCRIPTION
				        	"Supported SSID"
					::= { dot11WtpStatsEntry 5 }

wtpOnlineUsrNum				OBJECT-TYPE
					SYNTAX     	INTEGER 
					MAX-ACCESS 	read-only
					STATUS     	current
					DESCRIPTION
				        	"The total number of AP online user ."
					::= { dot11WtpStatsEntry 6 }

wtpUsrRequestConnect			OBJECT-TYPE
					SYNTAX     	Counter32 
					MAX-ACCESS 	read-only
					STATUS     	current
					DESCRIPTION
				        	"The total times that user request to connnect in."
					::= { dot11WtpStatsEntry 7 }

wtpResponseUsrConnect			OBJECT-TYPE
					SYNTAX     	Counter32 
					MAX-ACCESS 	read-only
					STATUS     	current
					DESCRIPTION
				        	"The total times that AP response user connection."
					::= { dot11WtpStatsEntry 8 }

wtpLoginSuccNum				OBJECT-TYPE
					SYNTAX     	Counter32 
					MAX-ACCESS 	read-only
					STATUS     	current
					DESCRIPTION
				        	"The total times that user login successfully."
					::= { dot11WtpStatsEntry 9 }

wtpLessResourceRefuseNewUsrMount 	OBJECT-TYPE
					SYNTAX     Counter32 
					MAX-ACCESS read-only
					STATUS     current
					DESCRIPTION
				        	"The total numbers of users who be refused to register because of less resources."
					::= { dot11WtpStatsEntry 10 }

wtpStatsDisassociated			OBJECT-TYPE
					SYNTAX     Counter32 
					MAX-ACCESS read-only
					STATUS     current
					DESCRIPTION
				        	"The total times that the system disconnect because of terminal exception."
					::= { dot11WtpStatsEntry 11 }

wtpUsrWirelessResoUseRate		OBJECT-TYPE
					SYNTAX     	DisplayString 
					MAX-ACCESS 	read-only
					STATUS     	current
					DESCRIPTION
				        	"The available rate of resources in the user side.(Wireless side)"
					::= { dot11WtpStatsEntry 12 }

wtpSSIDNum			 	OBJECT-TYPE
					SYNTAX     INTEGER
					MAX-ACCESS read-only
					STATUS     current
					DESCRIPTION
				        	"The total numbers of SSID."
					::= { dot11WtpStatsEntry 13 }

wtpAllStaAssTime			OBJECT-TYPE
					SYNTAX     TimeTicks
					MAX-ACCESS read-only
					STATUS     current
					DESCRIPTION
				        	"The total time that all the AP connectted."
					::= { dot11WtpStatsEntry 14 }

wtpConfigBSSIDNum			OBJECT-TYPE
					SYNTAX     INTEGER
					MAX-ACCESS read-only
					STATUS     current
					DESCRIPTION
				        	"The total numbers of configed BSSID."
					::= { dot11WtpStatsEntry 15 }
wtpInterfaceNum				OBJECT-TYPE
					SYNTAX     Integer32
					MAX-ACCESS read-only
					STATUS     current
					DESCRIPTION
				        	"The total numbers of interface.lixiang add for omc-20100820"
					::= { dot11WtpStatsEntry 16 }
wtpAssocSuccessTimes		 	OBJECT-TYPE
					SYNTAX     	Counter32 
					UNITS		"Times"
					MAX-ACCESS 	read-only
					STATUS     	current
					DESCRIPTION
				        	"The number of users(802.11b/g) associated success.(Times)"
					::= { dot11WtpStatsEntry 17 }
wtpRSSILowAssocFailTimes	OBJECT-TYPE
					SYNTAX     Counter32
					MAX-ACCESS read-only
					STATUS     current
					DESCRIPTION
				        	"low rssi assoc fail times"
					::= { dot11WtpStatsEntry 20 }
wtpHeartBeatAvgTimeDelay		OBJECT-TYPE
					SYNTAX     Integer32
					MAX-ACCESS read-only
					STATUS     current
					DESCRIPTION
				        	"The average time of AP heartbeat delay"
					::= { dot11WtpStatsEntry 21 }		
wtpEchoReqCnt		 		OBJECT-TYPE
					SYNTAX     	Counter32 
					MAX-ACCESS 	read-only
					STATUS     	current
					DESCRIPTION
				        	"The number of AC send to AP echo request pkts."
					::= { dot11WtpStatsEntry 22 }
wtpEchoRespLossCnt		 	OBJECT-TYPE
					SYNTAX     	Counter32 
					MAX-ACCESS 	read-only
					STATUS     	current
					DESCRIPTION
				        	"The number of no response echo pkts whitch AC send to AP."
					::= { dot11WtpStatsEntry 23 }
					
wtpResponseUsrConnectSuccess	 	OBJECT-TYPE
					SYNTAX     	Counter32 
					MAX-ACCESS 	read-only
					STATUS     	current
					DESCRIPTION
				        	"The total times that AP response user connection success."
					::= { dot11WtpStatsEntry 24 }
					
wtpResponseUsrConnectFail	 	OBJECT-TYPE
					SYNTAX     	Counter32 
					MAX-ACCESS 	read-only
					STATUS     	current
					DESCRIPTION
				        	"The total times that AP response user connection fail."
					::= { dot11WtpStatsEntry 25 }
wtpMountConReasFailTimes	 	OBJECT-TYPE
					SYNTAX     	Counter32 
					MAX-ACCESS 	read-only
					STATUS     	current
					DESCRIPTION
				        	"The total failed number of current reassociate(802.11bg).(Times)"
					::= { dot11WtpStatsEntry 26 }											

dot11RadioStatsTable OBJECT-TYPE
    SYNTAX      SEQUENCE OF Dot11RadioStatsEntry
    MAX-ACCESS  not-accessible
    STATUS      current
    DESCRIPTION
        "This table includes stats information of radio."
    ::= { wtpRadio 1 }

dot11RadioStatsEntry  OBJECT-TYPE
    SYNTAX      Dot11RadioStatsEntry
    MAX-ACCESS  not-accessible
    STATUS      current
    DESCRIPTION
        "Include stats information of radio."
    INDEX { wtpMacAddr,
	    wtpWirelessIfIndex }
    ::= { dot11RadioStatsTable 1 }
   
Dot11RadioStatsEntry ::=SEQUENCE{
	wtpRadCurrID				INTEGER,
	wtpCurTxPower				INTEGER,
	wtpPowerManage				INTEGER,
	wtpRxPower				INTEGER,
	wtpCurTakeFreqPoint			INTEGER,
	wtpCurConfChannel			INTEGER,
	wtpProtoMode				INTEGER,
	wtpSampleTime				TimeTicks,
	wtpTerminalConRate			INTEGER,
	wtpConfigAvailSpeed			DisplayString,
	wtpConfigForceSpeed			DisplayString,
	wtpRTSCTSEnable				INTEGER,
	wtpconfigBeaconFrameBlank		INTEGER
}

wtpRadCurrID		 		OBJECT-TYPE
					SYNTAX     	INTEGER 
					MAX-ACCESS 	read-only
					STATUS     	current
					DESCRIPTION
				        	"Current radio ID."
					::= { dot11RadioStatsEntry 1 }

wtpCurTxPower	 			OBJECT-TYPE
					SYNTAX     INTEGER 
					MAX-ACCESS read-write
					STATUS     current
					DESCRIPTION
				        	"The  current transmission power value."
					::= { dot11RadioStatsEntry 2 }

wtpPowerManage	 			OBJECT-TYPE
					SYNTAX     INTEGER{
							enable(1),
							disable(0)
							} 
					MAX-ACCESS read-only
					STATUS     current
					DESCRIPTION
				        	"If power management is open,the AP will adjust the launching power;
						If it is closed,it needs manual adjustment."
					::= { dot11RadioStatsEntry 3 }

wtpRxPower		 		OBJECT-TYPE
					SYNTAX     	INTEGER 
					MAX-ACCESS 	read-write
					STATUS     	current
					DESCRIPTION
				        	"The the received power value."
					::= { dot11RadioStatsEntry 4 }

wtpCurTakeFreqPoint	 		OBJECT-TYPE
					SYNTAX     	INTEGER 
					MAX-ACCESS 	read-only
					STATUS     	current
					DESCRIPTION
				        	"The frequency occupied by the AP."
					::= { dot11RadioStatsEntry 5 }


wtpCurConfChannel	 		OBJECT-TYPE
					SYNTAX     INTEGER(0..14) 
					MAX-ACCESS read-write
					STATUS     current
					DESCRIPTION
				        	"The channel of the configuration.(0 means auto)"
					::= { dot11RadioStatsEntry 6 }

wtpProtoMode	 			OBJECT-TYPE
					SYNTAX     INTEGER{
							   a(1),
							   b(2),
							   g(4),
							   bg(6),
							   an(8),
							   aan(9),
							   gn(16),
							   ggn(20),
							   bggn(22)
							}
					MAX-ACCESS read-write
					STATUS     current
					DESCRIPTION
				        	"AP protocol mode.(a, b, g, b/g, an, a/an, gn, g/gn, b/g/gn)"
					::= { dot11RadioStatsEntry 7 }


wtpSampleTime	 			OBJECT-TYPE
					SYNTAX     TimeTicks 
					UNITS	   "s"
					MAX-ACCESS read-only
					STATUS     current
					DESCRIPTION
				        	"The sample time.(s)"
					::= { dot11RadioStatsEntry 8 }

wtpTerminalConRate		 	OBJECT-TYPE
					SYNTAX     INTEGER 
					MAX-ACCESS read-write
					STATUS     current
					DESCRIPTION
				        	"The rate that configed terminal switch in.Select input value 540,480,360,240,120,110,90,60,55,20,10.While getting value,the value will be devided by 10bps(Units M/bps) "
					::= { dot11RadioStatsEntry 9 }

wtpConfigAvailSpeed 			OBJECT-TYPE
					SYNTAX     DisplayString 
					MAX-ACCESS read-only
					STATUS     current
					DESCRIPTION
				        	"The configed available speed congregation."
					::= { dot11RadioStatsEntry 10 }

wtpConfigForceSpeed	 		OBJECT-TYPE
					SYNTAX     OCTET STRING 
					MAX-ACCESS read-only
					STATUS     current
					DESCRIPTION
				        	"The configed enforced speed congregation."
					::= { dot11RadioStatsEntry 11 }

wtpRTSCTSEnable			 	OBJECT-TYPE
					SYNTAX     INTEGER{
							enable(1),
							disable(0)
							}
					MAX-ACCESS read-write
					STATUS     current
					DESCRIPTION
				        	"RTS/CTS whether start using."
					::= { dot11RadioStatsEntry 12 }

wtpconfigBeaconFrameBlank	 	OBJECT-TYPE
					SYNTAX     INTEGER(25..1000)
					MAX-ACCESS read-write
					STATUS     current
					DESCRIPTION
				        	"The configed beacon frame blank."
					::= { dot11RadioStatsEntry 13 }
dot11WtpParaTable OBJECT-TYPE
    SYNTAX      SEQUENCE OF Dot11WtpParaEntry
    MAX-ACCESS  not-accessible
    STATUS      current
    DESCRIPTION
        "This table includes information and settings of parameters."
    ::= { wtpStats 5 }

dot11WtpParaEntry  OBJECT-TYPE
    SYNTAX      Dot11WtpParaEntry
    MAX-ACCESS  not-accessible
    STATUS      current
    DESCRIPTION
        "Includes information and settings of parameters."
    INDEX { wtpMacAddr }
    ::= { dot11WtpParaTable 1 }


Dot11WtpParaEntry ::=SEQUENCE{
	wtpCurBssid				DisplayString,
	wtpGateAddr				IpAddress,
	wtpNetElementCode			DisplayString,
	wtpAddrMask				IpAddress,
	wtpsupportIfType			DisplayString,
	wtpRemoteRestartFun			INTEGER,
	wtpWorkMode				INTEGER,
	wtpReceiverSignalPWL			DisplayString,
	wtpMacConApAc				PhysAddress,
	wtpState				INTEGER,
	wtpDefenceDOSAttack			INTEGER,
	wtpIGMPSwitch				INTEGER,
	wtpBridgingWorkMode			INTEGER,
	wtpCurrAPMode				INTEGER,
	wtpSupport11B				INTEGER,
	wtpSupport11G				INTEGER,
	wtpAccessTime				DisplayString,
	wtpStartTime				DisplayString,
	wtpImagadataTime			DisplayString,
	wtpConfigUpdateTime			DisplayString,
	wtpIpv6NetPrefixLen			INTEGER
}

wtpCurBssid	 			OBJECT-TYPE
					SYNTAX     DisplayString 
					MAX-ACCESS read-only
					STATUS     current
					DESCRIPTION
				        	"The current BSSID of AP."
					::= { dot11WtpParaEntry 1 }

wtpGateAddr		 		OBJECT-TYPE
					SYNTAX     	IpAddress 
					MAX-ACCESS 	read-only
					STATUS     	current
					DESCRIPTION
				        	"The AP gateway address."
					::= { dot11WtpParaEntry 2 }

wtpNetElementCode 			OBJECT-TYPE
					SYNTAX     DisplayString(SIZE(1..32))
					MAX-ACCESS read-write
					STATUS     current
					DESCRIPTION
				        	"The net element of AP coding."
					::= { dot11WtpParaEntry 3 }

wtpAddrMask	 			OBJECT-TYPE
					SYNTAX     IpAddress 
					MAX-ACCESS read-only
					STATUS     current
					DESCRIPTION
				        	"AP address mask ."
					::= { dot11WtpParaEntry 4 }

wtpsupportIfType	 		OBJECT-TYPE
					SYNTAX     	DisplayString 
					MAX-ACCESS 	read-only
					STATUS     	current
					DESCRIPTION
				        	"AP interface type."
					::= { dot11WtpParaEntry 5 }

wtpRemoteRestartFun		 	OBJECT-TYPE
					SYNTAX     	INTEGER {
								used(1),
								unused(0)
							}
					MAX-ACCESS 	read-write
					STATUS     	current
					DESCRIPTION
				        	"AP remote reset function."
					::= { dot11WtpParaEntry 6 }

wtpWorkMode			 	OBJECT-TYPE
					SYNTAX     	INTEGER {
								fat-ap(1),
								bridge-mode(2),
								ap-and-brige(3)
								}
					MAX-ACCESS 	read-only
					STATUS     	current
					DESCRIPTION
				        	"AP work mode."
					::= { dot11WtpParaEntry 7 }

wtpReceiverSignalPWL			OBJECT-TYPE
					SYNTAX     	DisplayString
					UNITS		"V" 
					MAX-ACCESS 	read-only
					STATUS     	current
					DESCRIPTION
				        	"Receiver signal PWL."
					::= { dot11WtpParaEntry 8 }

wtpMacConApAc 				OBJECT-TYPE
					SYNTAX     PhysAddress 
					MAX-ACCESS read-only
					STATUS     current
					DESCRIPTION
				        	"The MAC address which the connection between AP and AC."
					::= { dot11WtpParaEntry 9 }

wtpState 				OBJECT-TYPE
					SYNTAX     INTEGER{
							join(2),
							configure(3),
							datacheck(4),
							run(5),
							quit(7),
							imagedata(8),
							bak_run(9)
							} 
					MAX-ACCESS read-only
					STATUS     current
					DESCRIPTION
				        	"Show the AP state.It has such state:join,configure,datacheck,run,quit,imagedata."
					::= { dot11WtpParaEntry 10 }

wtpDefenceDOSAttack		 	OBJECT-TYPE
					SYNTAX     INTEGER{
							enable(1),
							disable(0)
							}
					MAX-ACCESS read-write
					STATUS     current
					DESCRIPTION
				        	"Defence DOS attack."
					::= { dot11WtpParaEntry 11 }

wtpIGMPSwitch			 	OBJECT-TYPE
					SYNTAX     INTEGER{
							enable(1),
							disable(0)
							}
					MAX-ACCESS read-write
					STATUS     current
					DESCRIPTION
				        	"IGMP switch."
					::= { dot11WtpParaEntry 12 }

wtpBridgingWorkMode			OBJECT-TYPE
					SYNTAX     INTEGER{
							normal(1),
							Bridge(2),
							SemiBridge(3)
							}
					MAX-ACCESS read-write
					STATUS     current
					DESCRIPTION
				        	"AP bridging work mode."
					::= { dot11WtpParaEntry 13 }

wtpCurrAPMode				OBJECT-TYPE
					SYNTAX     INTEGER{
							normal(1),
							monitor(2),
							SemiMonitor(3)
							}
					MAX-ACCESS read-write
					STATUS     current
					DESCRIPTION
				        	"AP work mode includes:
							normal:AP support wlan login service
							monitor:AP monitor wireless envirment
							semimonitor:semi-monitor mode,doing net monitor while disengagement."
					::= { dot11WtpParaEntry 14 }
					
wtpSupport11B				OBJECT-TYPE
					SYNTAX     INTEGER{
							yes(1),
							no(2)
							}
					MAX-ACCESS read-write
					STATUS     current
					DESCRIPTION
				        	"AP work mode includes:
							yes:AP support 11B
							no:AP not support 11B."
					::= { dot11WtpParaEntry 15 }
				
wtpSupport11G				OBJECT-TYPE
					SYNTAX     INTEGER{
							yes(1),
							no(2)
							}
					MAX-ACCESS read-write
					STATUS     current
					DESCRIPTION
				        	"AP work mode includes:
							yes:AP support 11G
							no:AP not support 11G."
					::= { dot11WtpParaEntry 16 }
					
wtpAccessTime				OBJECT-TYPE
					SYNTAX     	DisplayString
					MAX-ACCESS 	read-only
					STATUS     	current
					DESCRIPTION
				        	"wtp access time."
					::= { dot11WtpParaEntry 17 }
					
wtpStartTime				OBJECT-TYPE
					SYNTAX     	DisplayString
					MAX-ACCESS 	read-only
					STATUS     	current
					DESCRIPTION
				        	"wtp start time."
					::= { dot11WtpParaEntry 18 }	

wtpImagadataTime			OBJECT-TYPE
					SYNTAX     	DisplayString
					MAX-ACCESS 	read-only
					STATUS     	current
					DESCRIPTION
				        	"wtp imagadata time."
					::= { dot11WtpParaEntry 19 }	

wtpConfigUpdateTime			OBJECT-TYPE
					SYNTAX     	DisplayString
					MAX-ACCESS 	read-only
					STATUS     	current
					DESCRIPTION
				        	"wtp configupdate time."
					::= { dot11WtpParaEntry 20 }	
wtpIpv6NetPrefixLen			OBJECT-TYPE
					SYNTAX     INTEGER(1..128)
					MAX-ACCESS read-only
					STATUS     current
					DESCRIPTION
				        	"The prefix length of Ipv6 net ."
					::= { dot11WtpParaEntry 22 }								
					
dot11WtpStatisticsTable OBJECT-TYPE
    SYNTAX      SEQUENCE OF Dot11WtpStatisticsEntry
    MAX-ACCESS  not-accessible
    STATUS      current
    DESCRIPTION
        "This table includes information and settings of wtp statistics."
    ::= { wtpStats 6 }

dot11WtpStatisticsEntry  OBJECT-TYPE
    SYNTAX      Dot11WtpStatisticsEntry
    MAX-ACCESS  not-accessible
    STATUS      current
    DESCRIPTION
        "Includes information and settings of wtp statistics."
    INDEX { wtpMacAddr }
    ::= { dot11WtpStatisticsTable 1 }


Dot11WtpStatisticsEntry ::=SEQUENCE{
	wtpRxPacketLossRate			DisplayString,
	wtpTxPacketLossRate			DisplayString,
	wtpDownBandwidthUtilization		DisplayString,
	wtpUpBandwidthUtilization		DisplayString,
	wtpReceiveRate				DisplayString,
	wtpSendRate				DisplayString
}

wtpRxPacketLossRate	 		OBJECT-TYPE
					SYNTAX     DisplayString 
					MAX-ACCESS read-only
					STATUS     current
					DESCRIPTION
				        	"The receive packet loss rate of AP."
					::= { dot11WtpStatisticsEntry 1 }

wtpTxPacketLossRate		 	OBJECT-TYPE
					SYNTAX     DisplayString 
					MAX-ACCESS read-only
					STATUS     current
					DESCRIPTION
				        	"The send packet loss rate of AP."
					::= { dot11WtpStatisticsEntry 2 }

wtpDownBandwidthUtilization		OBJECT-TYPE
					SYNTAX     DisplayString
					MAX-ACCESS read-only
					STATUS     current
					DESCRIPTION
				        	"The bandwidth utilization of downlink."
					::= { dot11WtpStatisticsEntry 3 }

wtpUpBandwidthUtilization		OBJECT-TYPE
					SYNTAX     DisplayString 
					MAX-ACCESS read-only
					STATUS     current
					DESCRIPTION
				        	"The bandwidth utilization of uplink."
					::= { dot11WtpStatisticsEntry 4 }
					
wtpReceiveRate				OBJECT-TYPE
					SYNTAX     DisplayString 
					MAX-ACCESS read-only
					STATUS     current
					DESCRIPTION
				        	"The ap receive rate."
					::= { dot11WtpStatisticsEntry 5 }
					
wtpSendRate				OBJECT-TYPE
					SYNTAX     DisplayString 
					MAX-ACCESS read-only
					STATUS     current
					DESCRIPTION
				        	"The ap send rate."
					::= { dot11WtpStatisticsEntry 6 }


					
dot11QuitWtpInfoTable OBJECT-TYPE
    SYNTAX      SEQUENCE OF Dot11QuitWtpInfoEntry
    MAX-ACCESS  not-accessible
    STATUS      current
    DESCRIPTION
        "This table includes information of quit wtp."
    ::= { wtpStats 7 }

dot11QuitWtpInfoEntry  OBJECT-TYPE
    SYNTAX      Dot11QuitWtpInfoEntry
    MAX-ACCESS  not-accessible
    STATUS      current
    DESCRIPTION
        "Includes information of quit wtp."
    INDEX { QuitWtpMacAddr }
    ::= { dot11QuitWtpInfoTable 1 }


Dot11QuitWtpInfoEntry ::=SEQUENCE{
	QuitWtpMacAddr			DisplayString,
	QuitWtpID			INTEGER,
	QuitWtpState			INTEGER
}
QuitWtpMacAddr			OBJECT-TYPE
				SYNTAX     DisplayString
				MAX-ACCESS read-only
				STATUS     current
				DESCRIPTION
			        	"Quit AP MAC."
				::= { dot11QuitWtpInfoEntry 1 }
					
QuitWtpID 			OBJECT-TYPE
				SYNTAX     INTEGER 
				MAX-ACCESS read-only
				STATUS     current
				DESCRIPTION
			        	"Quit AP ID."
				::= { dot11QuitWtpInfoEntry 2 }

QuitWtpState			OBJECT-TYPE
				SYNTAX     INTEGER{
						quit(7)
						} 
				MAX-ACCESS read-only
				STATUS     current
				DESCRIPTION
			        	"Quit AP state."
				::= { dot11QuitWtpInfoEntry 3 }					
				
dot11RunWtpInfoTable OBJECT-TYPE
    SYNTAX      SEQUENCE OF Dot11RunWtpInfoEntry
    MAX-ACCESS  not-accessible
    STATUS      current
    DESCRIPTION
        "This table includes information of run wtp."
    ::= { wtpStats 8 }

dot11RunWtpInfoEntry  OBJECT-TYPE
    SYNTAX      Dot11RunWtpInfoEntry
    MAX-ACCESS  not-accessible
    STATUS      current
    DESCRIPTION
        "Includes information of run wtp."
    INDEX { RunWtpMacAddr }
    ::= { dot11RunWtpInfoTable 1 }


Dot11RunWtpInfoEntry ::=SEQUENCE{
	RunWtpMacAddr			DisplayString,
	RunWtpID			INTEGER,
	RunWtpIP			IpAddress,
	RunWtpSN			DisplayString,	
	RunWtpState			INTEGER
}
RunWtpMacAddr			OBJECT-TYPE
				SYNTAX     DisplayString
				MAX-ACCESS read-only
				STATUS     current
				DESCRIPTION
			        	"Run AP MAC."
				::= { dot11RunWtpInfoEntry 1 }
					
RunWtpID 			OBJECT-TYPE
				SYNTAX     INTEGER 
				MAX-ACCESS read-only
				STATUS     current
				DESCRIPTION
			        	"Run AP ID."
				::= { dot11RunWtpInfoEntry 2 }
				
RunWtpIP 			OBJECT-TYPE
				SYNTAX     IpAddress 
				MAX-ACCESS read-only
				STATUS     current
				DESCRIPTION
			        	"Run AP IP."
				::= { dot11RunWtpInfoEntry 3 }
								
RunWtpSN			OBJECT-TYPE
				SYNTAX     DisplayString
				MAX-ACCESS read-only
				STATUS     current
				DESCRIPTION
			        	"Run AP SN."
				::= { dot11RunWtpInfoEntry 4 }								

RunWtpState			OBJECT-TYPE
				SYNTAX     INTEGER{
						run(5)
						} 
				MAX-ACCESS read-only
				STATUS     current
				DESCRIPTION
			        	"Run AP state."
				::= { dot11RunWtpInfoEntry 5 }					
										
dot11WtpChannelTable OBJECT-TYPE
    SYNTAX      SEQUENCE OF Dot11WtpChannelEntry
    MAX-ACCESS  not-accessible
    STATUS      current
    DESCRIPTION
        "This table includes settings and other information of channel."
    ::= { wtpBaseWtps 1 }

dot11WtpChannelEntry  OBJECT-TYPE
    SYNTAX      Dot11WtpChannelEntry
    MAX-ACCESS  not-accessible
    STATUS      current
    DESCRIPTION
        "Includes settings and other information of channel."
    INDEX { wtpMacAddr }
    ::= { dot11WtpChannelTable 1 }

Dot11WtpChannelEntry ::=SEQUENCE{
	wtpPathPhyErrPack			Counter32,
	wtpPathMacErrPack			Counter32,
	wtpPathFrameResRate			Counter32,
	wtpPathErrFrameRate			Counter32,
	wtpMonitorTime				TimeTicks,
	wtpSignalPathOfTerm			Integer32

}

wtpPathPhyErrPack			OBJECT-TYPE
					SYNTAX     	Counter32 
					MAX-ACCESS 	read-only
					STATUS     	current
					DESCRIPTION
				        	"The total number of mistake package of physical leve."
					::= { dot11WtpChannelEntry 1 }

wtpPathMacErrPack		 	OBJECT-TYPE
					SYNTAX     Counter32 
					MAX-ACCESS read-only
					STATUS     current
					DESCRIPTION
				        	"The total number of mistake package of MAC level in downlink channel(down-bound).(Update time less than 2 seconds)"
					::= { dot11WtpChannelEntry 2 }

wtpPathFrameResRate		 	OBJECT-TYPE
					SYNTAX     Counter32 
					MAX-ACCESS read-only
					STATUS     current
					DESCRIPTION
				        	"The total number of frames which resent by wireless signal channel during runtime ."
					::= { dot11WtpChannelEntry 3 }

wtpPathErrFrameRate		 	OBJECT-TYPE
					SYNTAX     Counter32 
					MAX-ACCESS read-only
					STATUS     current
					DESCRIPTION
				        	"Mistake frame rate on signal path."
					::= { dot11WtpChannelEntry 4 }

wtpMonitorTime		 		OBJECT-TYPE
					SYNTAX     TimeTicks 
					MAX-ACCESS read-only
					STATUS     current
					DESCRIPTION
				        	"The pass time of monitoring."
					::= { dot11WtpChannelEntry 5 }

wtpSignalPathOfTerm	 		OBJECT-TYPE
					SYNTAX     	Integer32 
					MAX-ACCESS 	read-only
					STATUS     	current
					DESCRIPTION
				        	"The terminal number which use the signal path."
					::= { dot11WtpChannelEntry 6 }



dot11WtpIfTable OBJECT-TYPE
    SYNTAX      SEQUENCE OF Dot11WtpIfEntry
    MAX-ACCESS  not-accessible
    STATUS      current
    DESCRIPTION
        "This table include settings and other information of interface."
    ::= { wtpInterface 1 }

dot11WtpIfEntry  OBJECT-TYPE
    SYNTAX      Dot11WtpIfEntry
    MAX-ACCESS  not-accessible
    STATUS      current
    DESCRIPTION
        "Include settings and information of interface."
    INDEX { wtpMacAddr,
    		wtpIfIndex
		}
    ::= { dot11WtpIfTable 1 }

Dot11WtpIfEntry ::=SEQUENCE{
	wtpIfIndex				INTEGER,
	wtpMTU					INTEGER,
	wtpIfSpeed				Gauge32,
	wtpIfPhyAddr				PhysAddress,
	wtpIfIntro				DisplayString,
	wtpIfName				DisplayString,
	wtpIfType				INTEGER,
	wtpIfAdminStatus			INTEGER,
	wtpIfOperStatus				INTEGER,
	wtpIfLastChange				TimeTicks,
	wtpIfUplinkRealtimeRate			Counter32,
	wtpIfDownlinkRealtimeRate		Counter32,
	wtpIfUplinkRealtimeKbyteRate		Counter32,
	wtpIfDownlinkRealtimeKbyteRate		Counter32	
}
wtpIfIndex				OBJECT-TYPE
					SYNTAX     	INTEGER 
					MAX-ACCESS 	read-only
					STATUS     	current
					DESCRIPTION
				        	"The interface number"
					::= { dot11WtpIfEntry 1 }

wtpMTU		 			OBJECT-TYPE
					SYNTAX     	INTEGER 
					MAX-ACCESS 	read-only
					STATUS     	current
					DESCRIPTION
				        	"The max transport unit which sent/received on an port.(byte)"
					::= { dot11WtpIfEntry 2 }

wtpIfSpeed	 			OBJECT-TYPE
					SYNTAX     	Gauge32 
					MAX-ACCESS 	read-write
					STATUS     	current
					DESCRIPTION
				        	"AP physical interface speed,include 10M/100M/1000M. The input must be 10/100/1000,otherwise you can't set it successfully."
					::= { dot11WtpIfEntry 3 }

wtpIfPhyAddr	 			OBJECT-TYPE
					SYNTAX     	PhysAddress 
					MAX-ACCESS 	read-only
					STATUS     	current
					DESCRIPTION
				        	"AP interface physical address."
					::= { dot11WtpIfEntry 4 }

wtpIfIntro			 	OBJECT-TYPE
					SYNTAX     	DisplayString(SIZE(0..255)) 
					MAX-ACCESS 	read-only
					STATUS     	current
					DESCRIPTION
				        	"The discription of AP interface information."
					::= { dot11WtpIfEntry 5 }
					
wtpIfName			 	OBJECT-TYPE
					SYNTAX     DisplayString
					MAX-ACCESS read-only
					STATUS     current
					DESCRIPTION
				        	"AP interface name."
					::= { dot11WtpIfEntry 6 }

wtpIfType			 	OBJECT-TYPE
					SYNTAX     INTEGER{
							Ethernet(6)
							}
					MAX-ACCESS read-only
					STATUS     current
					DESCRIPTION
				        	"AP physical interface type."
					::= { dot11WtpIfEntry 7 }

wtpIfAdminStatus	 		OBJECT-TYPE
					SYNTAX     INTEGER{
							up(1),
							down(0)
							}
					MAX-ACCESS read-write
					STATUS     current
					DESCRIPTION
				        	"AP physical  interface type status(up or down)."
					::= { dot11WtpIfEntry 8 }

wtpIfOperStatus	 			OBJECT-TYPE
					SYNTAX     INTEGER{
							up(1),
							down(0)
							}
					MAX-ACCESS read-only
					STATUS     current
					DESCRIPTION
				        	"AP physical  interface operate status."
					::= { dot11WtpIfEntry 9 }

wtpIfLastChange				OBJECT-TYPE
					SYNTAX     TimeTicks
					MAX-ACCESS read-only
					STATUS     current
					DESCRIPTION
				        	"The last time that AP changed current work mode."
					::= { dot11WtpIfEntry 10 }
					
wtpIfUplinkRealtimeRate			OBJECT-TYPE
					SYNTAX     Counter32
					MAX-ACCESS read-only
					STATUS     current
					DESCRIPTION
				        	"The uplink real time rate of AP eth interface."
					::= { dot11WtpIfEntry 11 }

wtpIfDownlinkRealtimeRate		OBJECT-TYPE
					SYNTAX     Counter32
					MAX-ACCESS read-only
					STATUS     current
					DESCRIPTION
				        	"The downlink real time rate of AP eth interface."
					::= { dot11WtpIfEntry 12 }
					
wtpIfUplinkRealtimeKbyteRate		OBJECT-TYPE
					SYNTAX     Counter32
					MAX-ACCESS read-only
					STATUS     current
					DESCRIPTION
				        	"The uplink real time rate of AP eth interface.(unit(Kbyte/s))"
					::= { dot11WtpIfEntry 13 }

wtpIfDownlinkRealtimeKbyteRate		OBJECT-TYPE
					SYNTAX     Counter32
					MAX-ACCESS read-only
					STATUS     current
					DESCRIPTION
				        	"The downlink real time rate of AP eth interface.(unit(Kbyte/s))"
					::= { dot11WtpIfEntry 14 }
					
dot11NewWtpIfTable OBJECT-TYPE
    SYNTAX      SEQUENCE OF Dot11NewWtpIfEntry
    MAX-ACCESS  not-accessible
    STATUS      current
    DESCRIPTION
        "This table include settings and other information of interface."
    ::= { wtpInterface 10 }

dot11NewWtpIfEntry  OBJECT-TYPE
    SYNTAX      Dot11NewWtpIfEntry
    MAX-ACCESS  not-accessible
    STATUS      current
    DESCRIPTION
        "Include settings and information of interface."
    INDEX { NewIfwtpID,
    		NewIfIndex
		}
    ::= { dot11NewWtpIfTable 1 }

Dot11NewWtpIfEntry ::=SEQUENCE{
	NewIfwtpID				INTEGER,
        NewIfIndex                              INTEGER,
	NewwtpMTU				INTEGER,
	NewwtpIfSpeed				Gauge32,
	NewwtpIfPhyAddr				PhysAddress,
	NewwtpIfIntro				DisplayString,
	NewwtpIfName				DisplayString,
	NewwtpIfType				INTEGER,
	NewwtpIfAdminStatus			INTEGER,
	NewwtpIfOperStatus			INTEGER,
	NewwtpIfLastChange			TimeTicks
}
NewIfwtpID				OBJECT-TYPE
					SYNTAX     	INTEGER 
					MAX-ACCESS 	read-only
					STATUS     	current
					DESCRIPTION
				        	"NewIfwtpID"
					::= { dot11NewWtpIfEntry 1 }

NewIfIndex		 			OBJECT-TYPE
					SYNTAX     	INTEGER 
					MAX-ACCESS 	read-only
					STATUS     	current
					DESCRIPTION
				        	"The IfIndex"
					::= { dot11NewWtpIfEntry 2 }

NewwtpMTU	 			OBJECT-TYPE
					SYNTAX     	INTEGER
					MAX-ACCESS 	read-only
					STATUS     	current
					DESCRIPTION
				        	"Wtp MTU."
					::= { dot11NewWtpIfEntry 3 }

NewwtpIfSpeed	 			OBJECT-TYPE
					SYNTAX     	Gauge32 
					MAX-ACCESS 	read-write
					STATUS     	current
					DESCRIPTION
				        	"AP physical interface speed,include 10M/100M/1000M. The input must be 10/100/1000,otherwise you can't set it successfully."
					::= { dot11NewWtpIfEntry 4 }

NewwtpIfPhyAddr			 	OBJECT-TYPE
					SYNTAX     	PhysAddress 
					MAX-ACCESS 	read-only
					STATUS     	current
					DESCRIPTION
				        	"AP interface physical address."
					::= { dot11NewWtpIfEntry 5 }
					
NewwtpIfIntro			 	OBJECT-TYPE
					SYNTAX     DisplayString(SIZE(0..255)) 
					MAX-ACCESS read-only
					STATUS     current
					DESCRIPTION
				        	"The discription of AP interface information."
					::= { dot11NewWtpIfEntry 6 }

NewwtpIfName			 	OBJECT-TYPE
					SYNTAX     DisplayString
					MAX-ACCESS read-only
					STATUS     current
					DESCRIPTION
				        	"AP interface name."
					::= { dot11NewWtpIfEntry 7 }

NewwtpIfType	 		        OBJECT-TYPE
					SYNTAX     INTEGER{
							Ethernet(6)
							}
					MAX-ACCESS read-only
					STATUS     current
					DESCRIPTION
				        	"AP physical interface type."
					::= { dot11NewWtpIfEntry 8 }

NewwtpIfAdminStatus	 		OBJECT-TYPE
					SYNTAX     INTEGER{
							up(1),
							down(0)
							}
					MAX-ACCESS read-write
					STATUS     current
					DESCRIPTION
				        	"AP physical  interface type status(up or down)."
					::= { dot11NewWtpIfEntry 9 }

NewwtpIfOperStatus			OBJECT-TYPE
					SYNTAX     INTEGER{
							up(1),
							down(0)
							}
					MAX-ACCESS read-only
					STATUS     current
					DESCRIPTION
				        	"AP physical  interface operate status."
					::= { dot11NewWtpIfEntry 10 }

NewwtpIfLastChange			OBJECT-TYPE
					SYNTAX     TimeTicks
					MAX-ACCESS read-only
					STATUS     current
					DESCRIPTION
				        	"The last time that AP changed current work mode."
					::= { dot11NewWtpIfEntry 11 }

dot11NewWtpWiredIfStatsTable OBJECT-TYPE
	    SYNTAX      SEQUENCE OF Dot11NewWtpWiredIfStatsEntry
	    MAX-ACCESS  not-accessible
	    STATUS      current
	    DESCRIPTION
	        "This table shows wired interface information."
	    ::= { wtpInterface 12 }

dot11NewWtpWiredIfStatsEntry  OBJECT-TYPE
    SYNTAX      Dot11NewWtpWiredIfStatsEntry
    MAX-ACCESS  not-accessible
    STATUS      current
    DESCRIPTION
        "Wired information."
    INDEX { NewWiredWtpID,
		NewwtpWiredIndex }
    ::= { dot11NewWtpWiredIfStatsTable 1 }
Dot11NewWtpWiredIfStatsEntry ::=SEQUENCE{
                NewWiredWtpID                   INTEGER,
                NewwtpWiredIndex                INTEGER,
		NewwtpWiredifInUcastPkts	Counter32,
		NewwtpWiredififInNUcastPkts	Counter32,
		NewwtpWiredififInOctets		Counter32,
		NewwtpWiredififInDiscardPkts	Counter32,
		NewwtpWiredififInErrors		Counter32,
		NewwtpWiredififOutUcastPkts	Counter32,
		NewwtpWiredififOutNUcastPkts	Counter32,
		NewwtpWiredififOutOctets	Counter32,
		NewwtpWiredififOutDiscardPkts	Counter32,
		NewwtpWiredififOutErrors	Counter32,
		NewwtpWiredififUpDwnTimes	Counter32
}
NewWiredWtpID			        OBJECT-TYPE
					SYNTAX     INTEGER 
					MAX-ACCESS read-only
					STATUS     current
					DESCRIPTION
				        	"NewWiredWtpID."
					::= { dot11NewWtpWiredIfStatsEntry 1 }

NewwtpWiredIndex			OBJECT-TYPE
					SYNTAX     INTEGER 
					MAX-ACCESS read-only
					STATUS     current
					DESCRIPTION
				        	"NewwtpWiredIndex."
					::= { dot11NewWtpWiredIfStatsEntry 2 }

NewwtpWiredifInUcastPkts			OBJECT-TYPE
					SYNTAX     Counter32 
					MAX-ACCESS read-only
					STATUS     current
					DESCRIPTION
				        	"Received the numbers of unicast packets."
					::= { dot11NewWtpWiredIfStatsEntry 3 }

NewwtpWiredififInNUcastPkts		OBJECT-TYPE
					SYNTAX     Counter32 
					MAX-ACCESS read-only
					STATUS     current
					DESCRIPTION
				        	"Received the numbers of non-unicast packets."
					::= { dot11NewWtpWiredIfStatsEntry 4 }

NewwtpWiredififInOctets			OBJECT-TYPE
					SYNTAX     Counter32 
					MAX-ACCESS read-only
					STATUS     current
					DESCRIPTION
				        	"The total number of received bytes."
					::= { dot11NewWtpWiredIfStatsEntry 5 }

NewwtpWiredififInDiscardPkts		OBJECT-TYPE
					SYNTAX     Counter32 
					MAX-ACCESS read-only
					STATUS     current
					DESCRIPTION
				        	"Discarded packets received ."
					::= { dot11NewWtpWiredIfStatsEntry 6 }

NewwtpWiredififInErrors			OBJECT-TYPE
					SYNTAX     Counter32 
					MAX-ACCESS read-only
					STATUS     current
					DESCRIPTION
				        	"Error packets received."
					::= { dot11NewWtpWiredIfStatsEntry 7 }

NewwtpWiredififOutUcastPkts		OBJECT-TYPE
					SYNTAX     Counter32 
					MAX-ACCESS read-only
					STATUS     current
					DESCRIPTION
				        	"The number of unicast packets sended."
					::= { dot11NewWtpWiredIfStatsEntry 8 }

NewwtpWiredififOutNUcastPkts		OBJECT-TYPE
					SYNTAX     Counter32 
					MAX-ACCESS read-only
					STATUS     current
					DESCRIPTION
				        	"The number of sent non-unicast packets."
					::= { dot11NewWtpWiredIfStatsEntry 9 }

NewwtpWiredififOutOctets			OBJECT-TYPE
					SYNTAX     Counter32 
					MAX-ACCESS read-only
					STATUS     current
					DESCRIPTION
				        	"The total number of bytes sent."
					::= { dot11NewWtpWiredIfStatsEntry 10 }

NewwtpWiredififOutDiscardPkts		OBJECT-TYPE
					SYNTAX     Counter32 
					MAX-ACCESS read-only
					STATUS     current
					DESCRIPTION
				        	"The number to send the packet which discarded."
					::= { dot11NewWtpWiredIfStatsEntry 11 }

NewwtpWiredififOutErrors		OBJECT-TYPE
					SYNTAX     Counter32 
					MAX-ACCESS read-only
					STATUS     current
					DESCRIPTION
				        	"The wrong number of packages which sent."
					::= { dot11NewWtpWiredIfStatsEntry 12 }

NewwtpWiredififUpDwnTimes		OBJECT-TYPE
					SYNTAX     Counter32 
					MAX-ACCESS read-only
					STATUS     current
					DESCRIPTION
				        	"Wired interface updown times."
					::= { dot11NewWtpWiredIfStatsEntry 13 }

dot11WtpBssTable OBJECT-TYPE
    SYNTAX      SEQUENCE OF Dot11WtpBssEntry
    MAX-ACCESS  not-accessible
    STATUS      current
    DESCRIPTION
        "This table includes information of BSSID."
    ::= { wtpBaseWtps 2 }

dot11WtpBssEntry  OBJECT-TYPE
    SYNTAX      Dot11WtpBssEntry
    MAX-ACCESS  not-accessible
    STATUS      current
    DESCRIPTION
        "Include BSSID information."
    INDEX { wtpMacAddr,
	    wtpBssCurrID }
    ::= { dot11WtpBssTable 1 }

Dot11WtpBssEntry ::=SEQUENCE{
	wtpBssCurrID				DisplayString,
	wtpDstBssidCurConfMaxConcurUser		INTEGER,
	wtpDstBssidCurConfMaxRate		INTEGER
}

wtpBssCurrID	 			OBJECT-TYPE
					SYNTAX     	DisplayString 
					MAX-ACCESS 	read-only
					STATUS     	current
					DESCRIPTION
				        	"The current AP BSSID."
					::= { dot11WtpBssEntry 1 }

wtpDstBssidCurConfMaxConcurUser	 	OBJECT-TYPE
					SYNTAX     INTEGER 
					MAX-ACCESS read-write
					STATUS     current
					DESCRIPTION
				        	"The max number of concurrent user which appointed BSSID can deal with."
					::= { dot11WtpBssEntry 2 }

wtpDstBssidCurConfMaxRate	 	OBJECT-TYPE
					SYNTAX     INTEGER 
					MAX-ACCESS read-write
					STATUS     current
					DESCRIPTION
				        	"The max concurrent rate which the device can deal with,the sum of up-bound rate and down-bound rate."
					::= { dot11WtpBssEntry 3 }


dot11WtpStaTable OBJECT-TYPE
    SYNTAX      SEQUENCE OF Dot11WtpStaEntry
    MAX-ACCESS  not-accessible
    STATUS      current
    DESCRIPTION
        "This table includes information of Station."
    ::= { wtpStation 1 }

dot11WtpStaEntry  OBJECT-TYPE
    SYNTAX      Dot11WtpStaEntry
    MAX-ACCESS  not-accessible
    STATUS      current
    DESCRIPTION
        "Include Station information."
    INDEX { wtpMacAddr
		,wtpStaMacAddr }
    ::= { dot11WtpStaTable 1 }

Dot11WtpStaEntry ::=SEQUENCE{
	wtpStaMacAddr				DisplayString,
	wtpStaIP				IpAddress,
	wtpWirelessClientSNR			Integer32,
	wtpTxTerminalPackMount			Counter32,
	wtpTxTerminalByteMount			Counter64,
	wtpTerminalRxPackMount			Counter32,
	wtpTerminalRxByteMount			Counter64,
	wtpTerminalResPack			Counter32,
	wtpTerminalResByte			Counter32,
	wtpTerminalRxErrPack			Counter32,
	wtpMacTermAddrUsrOnlineTime		TimeTicks,
	wtpMacTermAddrUsrTxSpd			Counter32,
	wtpMacTermAddrUsrRxSpd			Counter32,
	wtpMacTermAddrUsrAllThroughput		Counter32,
	wtpMacTermAPReceivedStaSignalStrength	DisplayString,
	wtpMacTermStaTxFragmentedPkts		Counter32,
	wtpMacTermAPTxFragmentedPkts		Counter32,
	wtpBelongAPID				INTEGER,
	wtpTerminalAccessTime			DisplayString,
	wtpBelongApName				DisplayString,
	wtpTerminalRecvDataPackMount		Counter32,
	wtpSendTerminalDataPackMount		Counter32,
	wtpTerminalTxDataRatePkts		OCTET STRING,	
	wtpTerminalRxDataRatePkts		OCTET STRING,	
	wtpTerminalTxSignalStrengthPkts		OCTET STRING,	
	APRxRates				DisplayString,
	APTxRates				DisplayString,
	MAXofRateset				DisplayString,
	wtpStaIPV6Addr				InetAddressIPv6
}

wtpStaMacAddr	 		OBJECT-TYPE
					SYNTAX     	DisplayString
					MAX-ACCESS 	read-only
					STATUS     	current
					DESCRIPTION
				        	"The terminal MAC address."
					::= { dot11WtpStaEntry 1 }

wtpStaIP				OBJECT-TYPE
					SYNTAX     	IpAddress
					MAX-ACCESS 	read-only
					STATUS     	current
					DESCRIPTION
				        	"Station IP."
					::= { dot11WtpStaEntry 2 }

wtpWirelessClientSNR	 		OBJECT-TYPE
					SYNTAX     	Integer32
					MAX-ACCESS 	read-only
					STATUS     	current
					DESCRIPTION
				        	"Wireless terminal SNR."
					::= { dot11WtpStaEntry 3 }

wtpTxTerminalPackMount	 	OBJECT-TYPE
					SYNTAX     Counter32 
					MAX-ACCESS read-only
					STATUS     current
					DESCRIPTION
				        	"The total number of packages which sending to the terminal."
					::= { dot11WtpStaEntry 4 }

wtpTxTerminalByteMount		OBJECT-TYPE
					SYNTAX     Counter64 
					MAX-ACCESS read-only
					STATUS     current
					DESCRIPTION
				        	"The total number of bytes which sent to the terminal.(KB)"
					::= { dot11WtpStaEntry 5 }

wtpTerminalRxPackMount	 	OBJECT-TYPE
					SYNTAX     Counter32 
					MAX-ACCESS read-only
					STATUS     current
					DESCRIPTION
				        	"The total number of packages which received from the terminal."
					::= { dot11WtpStaEntry 6 }

wtpTerminalRxByteMount	 	OBJECT-TYPE
					SYNTAX     Counter64 
					MAX-ACCESS read-only
					STATUS     current
					DESCRIPTION
				        	"The total number of bytes which received from the terminal.(KB)"
					::= { dot11WtpStaEntry 7 }

wtpTerminalResPack		 	OBJECT-TYPE
					SYNTAX     Counter32 
					MAX-ACCESS read-only
					STATUS     current
					DESCRIPTION
				        	"The total number of resent packages of the terminal."
					::= { dot11WtpStaEntry 8 }

wtpTerminalResByte		 	OBJECT-TYPE
					SYNTAX     Counter32 
					MAX-ACCESS read-only
					STATUS     current
					DESCRIPTION
				        	"The total number of resent bytes of the terminal.(KB)"
					::= { dot11WtpStaEntry 9 }

wtpTerminalRxErrPack	 	OBJECT-TYPE
					SYNTAX     Counter32 
					MAX-ACCESS read-only
					STATUS     current
					DESCRIPTION
				        	"The total number of mistake packages which received from the terminal."
					::= { dot11WtpStaEntry 10 }

wtpMacTermAddrUsrOnlineTime 		OBJECT-TYPE
					SYNTAX     	TimeTicks
					MAX-ACCESS	read-only
					STATUS    	current
					DESCRIPTION
				        	"The user online time which based on the mac address marked user."
					::= { dot11WtpStaEntry 11 }

wtpMacTermAddrUsrTxSpd	 	OBJECT-TYPE
					SYNTAX     	Counter32
					MAX-ACCESS 	read-only
					STATUS     	current
					DESCRIPTION
				        	"The user send speed which based on the mac address marked user."
					::= { dot11WtpStaEntry 12 }

wtpMacTermAddrUsrRxSpd	 	OBJECT-TYPE
					SYNTAX     	Counter32
					MAX-ACCESS 	read-only
					STATUS     	current
					DESCRIPTION
				        	"The user receive speed which based on the mac address marked user."
					::= { dot11WtpStaEntry 13 }

wtpMacTermAddrUsrAllThroughput 		OBJECT-TYPE
					SYNTAX     	Counter32
					MAX-ACCESS 	read-only
					STATUS     	current
					DESCRIPTION
				        	"The total thuoughput  which based on the mac address marked user."
					::= { dot11WtpStaEntry 14 }

wtpMacTermAPReceivedStaSignalStrength	OBJECT-TYPE
					SYNTAX     	DisplayString
					MAX-ACCESS 	read-only
					STATUS     	current
					DESCRIPTION
				        	"The current signal intensity that AP receives from terminal."
					::= { dot11WtpStaEntry 15 }

wtpMacTermStaTxFragmentedPkts		OBJECT-TYPE
					SYNTAX     	Counter32
					MAX-ACCESS 	read-only
					STATUS     	current
					DESCRIPTION
				        	"The total number of be neafed packets transmitted from terminal."
					::= { dot11WtpStaEntry 16 }

wtpMacTermAPTxFragmentedPkts		OBJECT-TYPE
					SYNTAX     	Counter32
					MAX-ACCESS 	read-only
					STATUS     	current
					DESCRIPTION
				        	"The total number of be neafed packets transmitted from AP to terminal."
					::= { dot11WtpStaEntry 17 }

wtpBelongAPID		 		OBJECT-TYPE
					SYNTAX     	INTEGER
					MAX-ACCESS 	read-only
					STATUS     	current
					DESCRIPTION
				        	"It has the same means as wtpMacAddr."
					::= { dot11WtpStaEntry 18 }
wtpTerminalAccessTime	 		OBJECT-TYPE
					SYNTAX     	DisplayString
					MAX-ACCESS 	read-only
					STATUS     	current
					DESCRIPTION
				        	"The terminal access time."
					::= { dot11WtpStaEntry 19 }
					
wtpBelongApName				OBJECT-TYPE
					SYNTAX     	DisplayString
					MAX-ACCESS 	read-only
					STATUS     	current
					DESCRIPTION
				        	"Ap name that the terminal accessed."
					::= { dot11WtpStaEntry 21 }

wtpTerminalRecvDataPackMount	 	OBJECT-TYPE
					SYNTAX     Counter32 
					MAX-ACCESS read-only
					STATUS     current
					DESCRIPTION
				        	"The number of data packages which received from the terminal"
					::= { dot11WtpStaEntry 22 }

wtpSendTerminalDataPackMount	 	OBJECT-TYPE
					SYNTAX     Counter32 
					MAX-ACCESS read-only
					STATUS     current
					DESCRIPTION
				        	"The number of data packages which send to the terminal"
					::= { dot11WtpStaEntry 23 }
					
wtpTerminalTxDataRatePkts		OBJECT-TYPE
					SYNTAX     OCTET STRING 
					MAX-ACCESS read-only
					STATUS     current
					DESCRIPTION
				        	"The total number of data rate pkts transmitted from AP to terminal."
					::= { dot11WtpStaEntry 24 }			
					
wtpTerminalRxDataRatePkts		OBJECT-TYPE
					SYNTAX     OCTET STRING 
					MAX-ACCESS read-only
					STATUS     current
					DESCRIPTION
				        	"The total number of data rate pkts transmitted from terminal."
					::= { dot11WtpStaEntry 25 }
					
wtpTerminalTxSignalStrengthPkts		OBJECT-TYPE
					SYNTAX     OCTET STRING 
					MAX-ACCESS read-only
					STATUS     current
					DESCRIPTION
				        	"The total number of signal strength pkts transmitted from AP to terminal."
					::= { dot11WtpStaEntry 26 }										
														
APRxRates				OBJECT-TYPE
					SYNTAX     DisplayString 
					MAX-ACCESS read-only
					STATUS     current
					DESCRIPTION
				        	"The user send speed which based on the mac address marked user."
					::= { dot11WtpStaEntry 27 }
					
APTxRates				OBJECT-TYPE
					SYNTAX     DisplayString 
					MAX-ACCESS read-only
					STATUS     current
					DESCRIPTION
				        	"The user receive speed which based on the mac address marked user."
					::= { dot11WtpStaEntry 28 }					
					
MAXofRateset				OBJECT-TYPE
					SYNTAX     DisplayString 
					MAX-ACCESS read-only
					STATUS     current
					DESCRIPTION
				        	"The max rate of consultation wireless rate set."
					::= { dot11WtpStaEntry 29 }
wtpStaIPV6Addr				OBJECT-TYPE
					SYNTAX     InetAddressIPv6 
					MAX-ACCESS read-only
					STATUS     current
					DESCRIPTION
				        	"The station ipv6 address."
					::= { dot11WtpStaEntry 30 }
					

dot11WtpWlanFaultTable 	OBJECT-TYPE
				SYNTAX	SEQUENCE OF Dot11WtpWlanFaultEntry
				MAX-ACCESS not-accessible
				STATUS		current
				DESCRIPTION
					"The table listing the dot11 wlan fault information."
				::={ wtpWlan 1 }

dot11WtpWlanFaultEntry	OBJECT-TYPE
			SYNTAX	Dot11WtpWlanFaultEntry
			MAX-ACCESS not-accessible
			STATUS	current
			DESCRIPTION
				"An entry (conceptual row) in the dot11WtpWlanFaultTable."
			INDEX	{ wtpMacAddr,
					wlanCurrID }
			::={ dot11WtpWlanFaultTable 1 }

Dot11WtpWlanFaultEntry ::=SEQUENCE {
	wirelessCRCFault			Counter32,
	wirelessPHYReceiveFault			Counter32,
	wirelessMICFault			Counter32,
	wirelessKEYFault			Counter32
}
wirelessCRCFault	 		OBJECT-TYPE
					SYNTAX     	Counter32
					MAX-ACCESS 	read-only
					STATUS     	current
					DESCRIPTION
				        	"CRC fault."
					::= { dot11WtpWlanFaultEntry 1 }

wirelessPHYReceiveFault	 		OBJECT-TYPE
					SYNTAX     	Counter32
					MAX-ACCESS 	read-only
					STATUS     	current
					DESCRIPTION
				        	"Phy receive fault."
					::= { dot11WtpWlanFaultEntry 2 }

wirelessMICFault	 		OBJECT-TYPE
					SYNTAX     	Counter32
					MAX-ACCESS 	read-only
					STATUS     	current
					DESCRIPTION
				        	"MIC fault."
					::= { dot11WtpWlanFaultEntry 3 }

wirelessKEYFault	 		OBJECT-TYPE
					SYNTAX     	Counter32
					MAX-ACCESS 	read-only
					STATUS     	current
					DESCRIPTION
				        	"Key decryption fault."
					::= { dot11WtpWlanFaultEntry 4 }

dot11WtpWlanDataPktsTable 	OBJECT-TYPE
				SYNTAX	SEQUENCE OF Dot11WtpWlanDataPktsEntry
				MAX-ACCESS not-accessible
				STATUS		current
				DESCRIPTION
					"The table listing the dot11 wlan data packets information."
				::={ wtpWlan 2 }

dot11WtpWlanDataPktsEntry		OBJECT-TYPE
				SYNTAX	Dot11WtpWlanDataPktsEntry
				MAX-ACCESS not-accessible
				STATUS	current
				DESCRIPTION
					"An entry (conceptual row) in the dot11WtpWlanDataPktsTable."
				INDEX	{ wtpMacAddr,
						wlanCurrID }
				::={ dot11WtpWlanDataPktsTable 1 }
Dot11WtpWlanDataPktsEntry ::=SEQUENCE {
	wtpSsidTxTermAllByte			Counter64,
	wtpSsidRxTermAllPack			Counter32,
	wtpSsidRxTermAllByte			Counter64,
	wtpSsidWirelessMacRxDataRightByte	Counter64,
	wtpSsidWirelessMacTxDataRightByte	Counter64,
	wtpSsidRxDataErrPack			Counter32,
	wtpNetWiredRxPack			Counter32,
	wtpSsidTxTermAllPack			Counter32,
	wtpNetWiredTxPack			Counter32,
	wtpSsidTxDataErrPkts			Counter32,
	wtpWirelessReTxPkts			Counter32,
	wtpWirelessErrPktsRate			DisplayString,
	wtpWirelessTxBroadcastMsgNum		Counter32,
	wtpStaUplinkMaxRate			Counter32,
	wtpStaDwlinkMaxRate			Counter32,
	wtpNetWiredRxErrPack			Counter32,
	wtpNetWiredRxRightPack			Counter32,
	wtpNetWiredRxByte			Counter64,
	wtpNetWiredTxByte			Counter64,
	wtpNetWiredTxErrPack			Counter32,
	wtpNetWiredTxRightPack			Counter32,
	wtpSsidTxDataAllPack			Counter32,
	wtpNetWiredRxErrPktsRate		DisplayString,
	wtpNetWiredTxErrPktsRate		DisplayString,
	wtpUsrWirelessMacRecvDataPack		Counter32
}
wtpSsidTxTermAllByte			OBJECT-TYPE
					SYNTAX     Counter64
					MAX-ACCESS read-only
					STATUS     current
					DESCRIPTION
				        	"The total bytes which sent to terminal(Appointed SSID).(KB)"
					::= { dot11WtpWlanDataPktsEntry 1 }

wtpSsidRxTermAllPack			OBJECT-TYPE
					SYNTAX     Counter32
					MAX-ACCESS read-only
					STATUS     current
					DESCRIPTION
				        	"The total packages which received from terminal(Appointed SSID)."
					::= { dot11WtpWlanDataPktsEntry 2 }

wtpSsidRxTermAllByte			OBJECT-TYPE
					SYNTAX     Counter64
					MAX-ACCESS read-only
					STATUS     current
					DESCRIPTION
				        	"The total bytes which received from terminal(Appointed SSID).(KB)"
					::= { dot11WtpWlanDataPktsEntry 3 }

wtpSsidWirelessMacRxDataRightByte	OBJECT-TYPE
					SYNTAX     Counter64
					MAX-ACCESS read-only
					STATUS     current
					DESCRIPTION
				        	"The received right bytes at MAC level appointed SSID."
					::= { dot11WtpWlanDataPktsEntry 4 }

wtpSsidWirelessMacTxDataRightByte	OBJECT-TYPE
					SYNTAX     Counter64
					MAX-ACCESS read-only
					STATUS     current
					DESCRIPTION
				        	"The sent total bytes at MAC level appointed SSID."
					::= { dot11WtpWlanDataPktsEntry 5 }

wtpSsidRxDataErrPack			OBJECT-TYPE
					SYNTAX     Counter32
					MAX-ACCESS read-only
					STATUS     current
					DESCRIPTION
				        	"The received wrong packages at MAC level appointed SSID."
					::= { dot11WtpWlanDataPktsEntry 6 }

wtpNetWiredRxPack			OBJECT-TYPE
					SYNTAX     Counter32
					MAX-ACCESS read-only
					STATUS     current
					DESCRIPTION
				        	"The received packages at network side(Wired side)."
					::= { dot11WtpWlanDataPktsEntry 7 }

wtpSsidTxTermAllPack			OBJECT-TYPE
					SYNTAX     Counter32
					MAX-ACCESS read-only
					STATUS     current
					DESCRIPTION
				        	"The sent packages at user side(Wireless side)."
					::= { dot11WtpWlanDataPktsEntry 8 }

wtpNetWiredTxPack			OBJECT-TYPE
					SYNTAX     Counter32
					MAX-ACCESS read-only
					STATUS     current
					DESCRIPTION
				        	"The sent packages at network side(Wired side)."
					::= { dot11WtpWlanDataPktsEntry 9 }
wtpSsidTxDataErrPkts			OBJECT-TYPE
					SYNTAX		Counter32
					MAX-ACCESS 	read-only
					STATUS		current
					DESCRIPTION
						"The total number of failed sent packets of wireless side."
					::={ dot11WtpWlanDataPktsEntry 10 }

wtpWirelessReTxPkts			OBJECT-TYPE
					SYNTAX		Counter32
					MAX-ACCESS 	read-only
					STATUS		current
					DESCRIPTION
						"The total number of resent packets of wireless side."
					::={ dot11WtpWlanDataPktsEntry 11 }
wtpWirelessErrPktsRate			OBJECT-TYPE
					SYNTAX     DisplayString 
					MAX-ACCESS read-only
					STATUS     current
					DESCRIPTION
				        	"The mistake packets rate on the wireless side."
					::= { dot11WtpWlanDataPktsEntry 12 }

wtpWirelessTxBroadcastMsgNum		OBJECT-TYPE
					SYNTAX     Counter32 
					MAX-ACCESS read-only
					STATUS     current
					DESCRIPTION
				        	"The total number of broadcast message box on the wireless side."
					::= { dot11WtpWlanDataPktsEntry 13 }
wtpStaUplinkMaxRate			OBJECT-TYPE
					SYNTAX     Counter32 
					MAX-ACCESS read-only
					STATUS     current
					DESCRIPTION
				        	"(Kbps)"
					::= { dot11WtpWlanDataPktsEntry 14 }

wtpStaDwlinkMaxRate			OBJECT-TYPE
					SYNTAX     Counter32 
					MAX-ACCESS read-only
					STATUS     current
					DESCRIPTION
				        	".(Kbps)"
					::= { dot11WtpWlanDataPktsEntry 15 }

wtpNetWiredRxErrPack			OBJECT-TYPE
					SYNTAX     Counter32
					MAX-ACCESS read-only
					STATUS     current
					DESCRIPTION
				        	"The total number of error recieved packets of wired side"
					::= { dot11WtpWlanDataPktsEntry 16 }
wtpNetWiredRxRightPack			OBJECT-TYPE
					SYNTAX     Counter32
					MAX-ACCESS read-only
					STATUS     current
					DESCRIPTION
				        	"The total number of successful recieved packets of wired side"
					::= { dot11WtpWlanDataPktsEntry 17 }
wtpNetWiredRxByte			OBJECT-TYPE
					SYNTAX     Counter64
					MAX-ACCESS read-only
					STATUS     current
					DESCRIPTION
				        	"The total number of  recieved bytes of wired side"
					::= { dot11WtpWlanDataPktsEntry 18 }
wtpNetWiredTxByte			OBJECT-TYPE
					SYNTAX     Counter64
					MAX-ACCESS read-only
					STATUS     current
					DESCRIPTION
				        	"The total number of  sent bytes of wired side"
					::= { dot11WtpWlanDataPktsEntry 19 }
wtpNetWiredTxErrPack			OBJECT-TYPE
					SYNTAX     Counter32
					MAX-ACCESS read-only
					STATUS     current
					DESCRIPTION
				        	"The total number of  sent error packages of wired side"
					::= { dot11WtpWlanDataPktsEntry 20 }
wtpNetWiredTxRightPack			OBJECT-TYPE
					SYNTAX     Counter32
					MAX-ACCESS read-only
					STATUS     current
					DESCRIPTION
				        	"The total number of  sent right packages of wired side"
					::= { dot11WtpWlanDataPktsEntry 21 }				
		
wtpSsidTxDataAllPack			OBJECT-TYPE
					SYNTAX     Counter32
					MAX-ACCESS read-only
					STATUS     current
					DESCRIPTION
				        	"The total number of sent data packets."
					::= { dot11WtpWlanDataPktsEntry 22 }	
	
wtpNetWiredRxErrPktsRate		OBJECT-TYPE
					SYNTAX     DisplayString 
					MAX-ACCESS read-only
					STATUS     current
					DESCRIPTION
				        	"The mistake packets rate of recieved on the wired side."
					::= { dot11WtpWlanDataPktsEntry 23 }						
					
wtpNetWiredTxErrPktsRate		OBJECT-TYPE
					SYNTAX     DisplayString 
					MAX-ACCESS read-only
					STATUS     current
					DESCRIPTION
				        	"The mistake packets rate of sent on the wired side."
					::= { dot11WtpWlanDataPktsEntry 24 }	

wtpUsrWirelessMacRecvDataPack		OBJECT-TYPE
					SYNTAX     Counter32
					MAX-ACCESS read-only
					STATUS     current
					DESCRIPTION
				        	"The receive packages at user side(Wireless side)."
					::= { dot11WtpWlanDataPktsEntry 27 }


				
	
dot11WtpWlanStatsTable 	OBJECT-TYPE
				SYNTAX	SEQUENCE OF Dot11WtpWlanStatsEntry
				MAX-ACCESS not-accessible
				STATUS		current
				DESCRIPTION
					"The table listing the dot11 wlan status information."
				::={ wtpWlan 3 }

dot11WtpWlanStatsEntry	OBJECT-TYPE
			SYNTAX	Dot11WtpWlanStatsEntry
			MAX-ACCESS not-accessible
			STATUS	current
			DESCRIPTION
				"An entry (conceptual row) in the dot11WtpWlanStatsTable."
			INDEX	{ wtpMacAddr,
					wlanCurrID }
			::={ dot11WtpWlanStatsTable 1 }

Dot11WtpWlanStatsEntry ::=SEQUENCE {
	wlanCurrID				INTEGER,
	wtpEAPAuthenSupport			INTEGER,
	wtpLoadBalance				INTEGER,
	wirelessSSID				DisplayString,
	wtpSsidBroadcast			TruthValue,
	wtpConfSecurMech			INTEGER,
	wtpSsidCurrOnlineUsrNum			Integer32,
	wtpAcAppointDistOnlineUsrNum		INTEGER,
	wtpConRadiusServerIP			IpAddress,
	wtpConRadiusServerPort			INTEGER,
	wtpSSIDPriority				INTEGER,
	wtpAttachedFlowThreshold 		INTEGER,
	wtpUsrNumAppendThreshold		INTEGER,
	wtpL2Insulate 				INTEGER

}
wlanCurrID				OBJECT-TYPE
				    	SYNTAX     INTEGER
				    	MAX-ACCESS read-only
				    	STATUS     current
				    	DESCRIPTION
				            	"The wlan's ID."
				    	::= { dot11WtpWlanStatsEntry 1 }

wtpEAPAuthenSupport	 		OBJECT-TYPE
					SYNTAX		INTEGER	{
								enable-EAP-Authentication(0),
								disable-EAP-Authentication(1),
								not-Supporting-EAP-Authentication(2)
								}
					MAX-ACCESS 	read-only
					STATUS		current
					DESCRIPTION
						"The EPA module whether open."
					::={ dot11WtpWlanStatsEntry 2 }

wtpLoadBalance				OBJECT-TYPE
					SYNTAX     TruthValue 
					MAX-ACCESS read-only
					STATUS     current
					DESCRIPTION
				        	"Based on the total number of users for load balancing."
					::= { dot11WtpWlanStatsEntry 3 }

wirelessSSID				OBJECT-TYPE
					SYNTAX     	DisplayString
					MAX-ACCESS 	read-only
					STATUS     	current
					DESCRIPTION
				        	"SSID."
					::= { dot11WtpWlanStatsEntry 4 }


wtpSsidBroadcast		 	OBJECT-TYPE
					SYNTAX     TruthValue 
					MAX-ACCESS read-write
					STATUS     current
					DESCRIPTION
				        	"The ssid is whether broadcast."
					::= { dot11WtpWlanStatsEntry 5 }

wtpConfSecurMech	 		OBJECT-TYPE
					SYNTAX     INTEGER{
							openSystem (0),
							sharedKey(1),
							dot11x(2),
							WPA-P(3),
							WPA2-P(4),
							WPA-E(5),
							WPA2-E(6),
							MD5(7),
							WAPI-PSK(8),
							WAPI-AUTH(9)
							}
					MAX-ACCESS read-write
					STATUS     current
					DESCRIPTION
				        	"The configed mechanism such as open system or shared key(o means no secyurity mechanism)."
					::= { dot11WtpWlanStatsEntry 6 }

wtpSsidCurrOnlineUsrNum			OBJECT-TYPE
					SYNTAX     Integer32
					MAX-ACCESS read-only
					STATUS     current
					DESCRIPTION
				        	"The appointed SSID online user number."
					::= { dot11WtpWlanStatsEntry 7 }



wtpAcAppointDistOnlineUsrNum 		OBJECT-TYPE
					SYNTAX		INTEGER	
					MAX-ACCESS 	read-only
					STATUS		current
					DESCRIPTION
						"The total number of online user at appointed district."
					::={ dot11WtpWlanStatsEntry 8 }

wtpConRadiusServerIP 			OBJECT-TYPE
					SYNTAX		IpAddress
					MAX-ACCESS 	read-only
					STATUS		current
					DESCRIPTION
						"Radius server IP address."
					::={ dot11WtpWlanStatsEntry 9 }

wtpConRadiusServerPort	 		OBJECT-TYPE
					SYNTAX		INTEGER
					MAX-ACCESS 	read-only
					STATUS		current
					DESCRIPTION
						"Radius server port number."
					::={ dot11WtpWlanStatsEntry 10 }

wtpSSIDPriority			 	OBJECT-TYPE
					SYNTAX     INTEGER
					MAX-ACCESS read-write
					STATUS     current
					DESCRIPTION
				        	"SSID priority"
					::= { dot11WtpWlanStatsEntry 11 }

wtpAttachedFlowThreshold	 	OBJECT-TYPE
					SYNTAX     INTEGER(1..30)
					MAX-ACCESS read-write
					STATUS     current
					DESCRIPTION
				        	"Traffic load balancing threshold."
					::= { dot11WtpWlanStatsEntry 12 }

wtpUsrNumAppendThreshold	 	OBJECT-TYPE
					SYNTAX     INTEGER(1..10)
					MAX-ACCESS read-write
					STATUS     current
					DESCRIPTION
				        	"Load balancing the number of users threshold."
					::= { dot11WtpWlanStatsEntry 13 }

wtpL2Insulate			 	OBJECT-TYPE
					SYNTAX     INTEGER{
							open(1),
							close(0)
							}
					MAX-ACCESS read-write
					STATUS     current
					DESCRIPTION
				        	"L2 insulate whether open."
					::= { dot11WtpWlanStatsEntry 14 }

dot11RadioParaTable OBJECT-TYPE
    SYNTAX      SEQUENCE OF Dot11RadioParaEntry
    MAX-ACCESS  not-accessible
    STATUS      current
    DESCRIPTION
        "This table shows Radio para information."
    ::= { wtpRadio 2 }

dot11RadioParaEntry  OBJECT-TYPE
    SYNTAX      Dot11RadioParaEntry
    MAX-ACCESS  not-accessible
    STATUS      current
    DESCRIPTION
        "Radio para information."
    INDEX { wtpMacAddr,
		wtpWirelessIfIndex }
    ::= { dot11RadioParaTable 1 }
   
Dot11RadioParaEntry ::=SEQUENCE{
	wtpAntAPlus				Integer32,
	wtpAntBGPlus				Integer32,
	wtpSignalPathMode			DisplayString,
	wtpSignalSNR				DisplayString,
	wtpFrequencyHopTimes			INTEGER,
	wtpFreHopDetectTime			INTEGER,
	wtpConfigLongRetransThreshold		INTEGER,
	wtpMessageNeafThreshold			INTEGER,
	wtpRTSThreshold				INTEGER,
	wtpSignalAveIntensity			INTEGER,
	wtpPreambleLen				INTEGER
}

wtpAntAPlus			 	OBJECT-TYPE
					SYNTAX     Integer32 
					MAX-ACCESS read-only
					STATUS     current
					DESCRIPTION
				        	"Antenna plus(802.11a)."
					::= { dot11RadioParaEntry 1 }

wtpAntBGPlus			 	OBJECT-TYPE
					SYNTAX     Integer32 
					MAX-ACCESS read-only
					STATUS     current
					DESCRIPTION
				        	"Antenna plus(802.11b/g)."
					::= { dot11RadioParaEntry 2 }

wtpSignalPathMode		 	OBJECT-TYPE
					SYNTAX     DisplayString
					MAX-ACCESS read-write
					STATUS     current
					DESCRIPTION
				        	"Signal path mode."
					::= { dot11RadioParaEntry 3 }

wtpSignalSNR			 	OBJECT-TYPE
					SYNTAX     DisplayString
					MAX-ACCESS read-only
					STATUS     current
					DESCRIPTION
				        	"Signal SNR."
					::= { dot11RadioParaEntry 4 }

wtpFrequencyHopTimes		 	OBJECT-TYPE
					SYNTAX     INTEGER
					MAX-ACCESS read-only
					STATUS     current
					DESCRIPTION
				        	"The times that change signal path because of shuning Frequency interference."
					::= { dot11RadioParaEntry 5 }

wtpFreHopDetectTime		 	OBJECT-TYPE
					SYNTAX     INTEGER
					MAX-ACCESS read-write
					STATUS     current
					DESCRIPTION
				        	"The pass-time that change signal path because of shuning Frequency interference."
					::= { dot11RadioParaEntry 6 }
					


wtpConfigLongRetransThreshold 		OBJECT-TYPE
					SYNTAX     INTEGER 
					MAX-ACCESS read-write
					STATUS     current
					DESCRIPTION
				        	"The value of configed long retransmission threshold."
					::= { dot11RadioParaEntry 7 }

wtpMessageNeafThreshold		 	OBJECT-TYPE
					SYNTAX     INTEGER 
					MAX-ACCESS read-write
					STATUS     current
					DESCRIPTION
				        	"The value of message neaf threshold."
					::= { dot11RadioParaEntry 8 }

wtpRTSThreshold			 	OBJECT-TYPE
					SYNTAX     INTEGER 
					MAX-ACCESS read-write
					STATUS     current
					DESCRIPTION
				        	"The value of RTS threshold."
					::= { dot11RadioParaEntry 9 }

wtpSignalAveIntensity		 	OBJECT-TYPE
					SYNTAX     INTEGER 
					MAX-ACCESS read-write
					STATUS     current
					DESCRIPTION
				        	"The average intensity of signal."
					::= { dot11RadioParaEntry 10 }

wtpPreambleLen				OBJECT-TYPE
					SYNTAX     INTEGER{
							short(1),
							long(2)
								}
					MAX-ACCESS read-write
					STATUS     current
					DESCRIPTION
				        	"The Preamble length."
					::= { dot11RadioParaEntry 11 }
--***********************************************************************************************************
dot11ConfigRadioTable OBJECT-TYPE
    SYNTAX      SEQUENCE OF Dot11ConfigRadioEntry
    MAX-ACCESS  not-accessible
    STATUS      current
    DESCRIPTION
        "This table shows Radio and config radio."
    ::= { wtpRadio 3 }

dot11ConfigRadioEntry  OBJECT-TYPE
    SYNTAX      Dot11ConfigRadioEntry
    MAX-ACCESS  not-accessible
    STATUS      current
    DESCRIPTION
        "Radio and config radio."
    INDEX { wtpMacAddr,
		wtpWirelessIfIndex }
    ::= { dot11ConfigRadioTable 1 }
   
Dot11ConfigRadioEntry ::=SEQUENCE{
	radioChannel				INTEGER,
	radioTxPower				INTEGER,
	radioType				INTEGER,
	radioSpeed				INTEGER,
	radioBeacon				INTEGER,
	radioFragThreshold			INTEGER,
	radioDtim				INTEGER,
	radioRTS				INTEGER,
	radioLeadCode				INTEGER,
	radioShortRetry				INTEGER,
	radioLongRetry				INTEGER,
	radioService				INTEGER,
	radioMaxSpeed				INTEGER,
	radioMaxFlow				INTEGER,
	radioBindWlan				DisplayString,
	radioDelbindWlan			DisplayString,
        radioBindQos                            DisplayString,
        radioDelbindQos                         DisplayString,
        radioAmpduSwitch			INTEGER,
        radioCwmode				INTEGER,
        radioShortGISwitch			INTEGER,
        radioAmsduSwitch			INTEGER,
        radioMCS				DisplayString,
        radio11nSwitch				INTEGER,
        OnlyAllow11nStaAccess                   TruthValue,
	radioRole				INTEGER,
	radioChanelUsage			INTEGER,
	radioChanelChangeNum			INTEGER,
	radioChannelWidth			INTEGER,
	radioNoiseFloor				INTEGER
}
radioChannel				OBJECT-TYPE
					SYNTAX     INTEGER 
					MAX-ACCESS read-write
					STATUS     current
					DESCRIPTION
				        	"Radio channel,the range is form 149 to 153 when radio type is 11a,the other type is range from 1 to 11."
					::= { dot11ConfigRadioEntry 1 }

radioTxPower				OBJECT-TYPE
					SYNTAX     INTEGER(1..27) 
					MAX-ACCESS read-write
					STATUS     current
					DESCRIPTION
				        	"Transmission power(UNITS DB)."
					::= { dot11ConfigRadioEntry 2 }

radioType				OBJECT-TYPE
					SYNTAX     INTEGER{
							   a(1),
							   b(2),
							   g(4),
							   bg(6),
							   an(8),
							   aan(9),
							   gn(16),
							   ggn(20),
							   bggn(22)							
							   }
					MAX-ACCESS read-write
					STATUS     current
					DESCRIPTION
				        	"Radio type."
					::= { dot11ConfigRadioEntry 3 }

radioSpeed				OBJECT-TYPE
					SYNTAX     INTEGER
					MAX-ACCESS read-write
					STATUS     current
					DESCRIPTION
				        	"Speed.(1,2,5.5,6,9,11,12,18,24,36,48,54M/bps)"
					::= { dot11ConfigRadioEntry 4 }

radioBeacon				OBJECT-TYPE
					SYNTAX     INTEGER(25..1000)
					MAX-ACCESS read-write
					STATUS     current
					DESCRIPTION
				        	"Beacon.(Units ms)"
					::= { dot11ConfigRadioEntry 5 }

radioFragThreshold				OBJECT-TYPE
					SYNTAX     INTEGER(256..2346)
					MAX-ACCESS read-write
					STATUS     current
					DESCRIPTION
				        	"Beaf.(Units byte)"
					::= { dot11ConfigRadioEntry 6 }

radioDtim				OBJECT-TYPE
					SYNTAX     INTEGER(1..15)
					MAX-ACCESS read-write
					STATUS     current
					DESCRIPTION
				        	"Dtim."
					::= { dot11ConfigRadioEntry 7 }

radioRTS				OBJECT-TYPE
					SYNTAX     INTEGER(256..2346)
					MAX-ACCESS read-write
					STATUS     current
					DESCRIPTION
				        	"RTS."
					::= { dot11ConfigRadioEntry 8 }

radioLeadCode				OBJECT-TYPE
					SYNTAX     INTEGER{
							short(1),
							long(2)
							}
					MAX-ACCESS read-write
					STATUS     current
					DESCRIPTION
				        	"Lead code."
					::= { dot11ConfigRadioEntry 9 }

radioShortRetry				OBJECT-TYPE
					SYNTAX     INTEGER(1..15)
					MAX-ACCESS read-write
					STATUS     current
					DESCRIPTION
				        	"Short retry."
					::= { dot11ConfigRadioEntry 10 }

radioLongRetry				OBJECT-TYPE
					SYNTAX     INTEGER(1..15)
					MAX-ACCESS read-write
					STATUS     current
					DESCRIPTION
				        	"Long retry."
					::= { dot11ConfigRadioEntry 11 }

radioService				OBJECT-TYPE
					SYNTAX     INTEGER{
							disable(1),
							enable(2)
								}
					MAX-ACCESS read-write
					STATUS     current
					DESCRIPTION
				        	"Radio service."
					::= { dot11ConfigRadioEntry 12 }

radioMaxSpeed				OBJECT-TYPE
					SYNTAX     INTEGER 
					MAX-ACCESS read-write
					STATUS     current
					DESCRIPTION
				        	"Max speed.(10,20,55,60,90,110,120,180,240,360,480,540M/bps)"
					::= { dot11ConfigRadioEntry 13 }

radioMaxFlow				OBJECT-TYPE
					SYNTAX     INTEGER(1..108)
					MAX-ACCESS read-write
					STATUS     current
					DESCRIPTION
				        	"Max flow.(Units M)"
					::= { dot11ConfigRadioEntry 14 }

radioBindWlan				OBJECT-TYPE
					SYNTAX     DisplayString 
					MAX-ACCESS read-write
					STATUS     current
					DESCRIPTION
				        	"When radio bound wlan, should bind one by one."
					::= { dot11ConfigRadioEntry 15 }
					
radioDelbindWlan			OBJECT-TYPE
					SYNTAX     DisplayString
					MAX-ACCESS read-write
					STATUS     current
					DESCRIPTION
				        	"When radio unbound wlan, should unbind one by one."
					::= { dot11ConfigRadioEntry 16 }
radioBindQos				OBJECT-TYPE
					SYNTAX     DisplayString 
					MAX-ACCESS read-write
					STATUS     current
					DESCRIPTION
				        	"Bind Qos."
					::= { dot11ConfigRadioEntry 17 }
					
radioDelbindQos			        OBJECT-TYPE
					SYNTAX     DisplayString
					MAX-ACCESS read-write
					STATUS     current
					DESCRIPTION
				        	"Delete Binded Qos."
					::= { dot11ConfigRadioEntry 18 }		
					
radioAmpduSwitch		        OBJECT-TYPE
					SYNTAX     INTEGER{
							off(0),
							on(1)
							}
					MAX-ACCESS read-write
					STATUS     current
					DESCRIPTION
				        	"A-MPDU Switch."
					::= { dot11ConfigRadioEntry 19 }

radioCwmode			        OBJECT-TYPE
					SYNTAX     INTEGER{
							ht20(0),
							ht20-ht40(1),
							ht40(2)
							}
					MAX-ACCESS read-write
					STATUS     current
					DESCRIPTION
				        	"Cwmode."
					::= { dot11ConfigRadioEntry 20 }        
	
radioShortGISwitch		        OBJECT-TYPE
					SYNTAX     INTEGER{
							off(0),
							on(1)
							}
					MAX-ACCESS read-write
					STATUS     current
					DESCRIPTION
				        	"Short GI Switch."
					::= { dot11ConfigRadioEntry 21 }    
					
radioAmsduSwitch		        OBJECT-TYPE
					SYNTAX     INTEGER{
							off(0),
							on(1)
							}
					MAX-ACCESS read-write
					STATUS     current
					DESCRIPTION
				        	"A-MSDU Switch."
					::= { dot11ConfigRadioEntry 22 }	
		
radioMCS		        	OBJECT-TYPE
					SYNTAX     DisplayString
					MAX-ACCESS read-write
					STATUS     current
					DESCRIPTION
				        	"Modulation and Coding Scheme."
					::= { dot11ConfigRadioEntry 23 }
					
radio11nSwitch			        OBJECT-TYPE
					SYNTAX     INTEGER{
							off(0),
							on(1)
							}
					MAX-ACCESS read-write
					STATUS     current
					DESCRIPTION
				        	"802.11n Switch."
					::= { dot11ConfigRadioEntry 24 }												             

OnlyAllow11nStaAccess			OBJECT-TYPE
					SYNTAX     TruthValue
					MAX-ACCESS read-write
					STATUS     current
					DESCRIPTION
				        	"Whether only allows 11N terminal access."
					::= { dot11ConfigRadioEntry 25 }  	

radioRole				OBJECT-TYPE
					SYNTAX     INTEGER{
							Clint(1),
							Other(2),
							AP(6),
							Mesh(9)							
							   }
					MAX-ACCESS read-only
					STATUS     current
					DESCRIPTION
				        	"Radio Role."
					::= { dot11ConfigRadioEntry 28 }	

radioChanelUsage			OBJECT-TYPE
					SYNTAX     INTEGER
					MAX-ACCESS read-only
					STATUS     current
					DESCRIPTION
				        	"Radio chanel usage."
					::= { dot11ConfigRadioEntry 29 }

radioChanelChangeNum			OBJECT-TYPE
					SYNTAX     INTEGER
					MAX-ACCESS read-only
					STATUS     current
					DESCRIPTION
				        	"Radio chanel change number."
					::= { dot11ConfigRadioEntry 30 }

radioChannelWidth			OBJECT-TYPE
					SYNTAX     INTEGER
					MAX-ACCESS read-only
					STATUS     current
					DESCRIPTION
				        	"Radio channel width."
					::= { dot11ConfigRadioEntry 31 }

radioNoiseFloor				OBJECT-TYPE
					SYNTAX     INTEGER
					MAX-ACCESS read-only
					STATUS     current
					DESCRIPTION
				        	"Radio noise floor."
					::= { dot11ConfigRadioEntry 32 }
        								
--**********************************************************************************************************
dot11RadioStatisticsTable OBJECT-TYPE
    SYNTAX      SEQUENCE OF Dot11RadioStatisticsEntry
    MAX-ACCESS  not-accessible
    STATUS      current
    DESCRIPTION
        "Radio statistics."
    ::= { wtpRadio 4 }

dot11RadioStatisticsEntry  OBJECT-TYPE
    SYNTAX      Dot11RadioStatisticsEntry
    MAX-ACCESS  not-accessible
    STATUS      current
    DESCRIPTION
        "Radio statistics."
    INDEX { wtpRadCurrID,
		bssid }
    ::= { dot11RadioStatisticsTable 1 }
   
Dot11RadioStatisticsEntry ::=SEQUENCE{
	bssid					INTEGER,
	wirelessUpFlow				Counter64,
	wirelessDownFlow			Counter64,
	channelDownAllPkts			Counter64,
	channelDownAllDropPkts			Counter64,
	channelDownAllMacErrPkts		Counter64,
	channelDownAllResPkts			Counter64,
	channelUpAllFrames			Counter64,
	channelDownAllFrames			Counter64,
	channelDownAllErrFrames			Counter64,
	channelDownAllDropFrames		Counter64,
	channelDownAllResFrames			Counter64,
	channelUpAllDropFrames			Counter64,
	channelUpAllResFrames			Counter64
}
bssid					OBJECT-TYPE
					SYNTAX     INTEGER 
					MAX-ACCESS read-only
					STATUS     current
					DESCRIPTION
				        	"bssid."
					::= { dot11RadioStatisticsEntry 1 }

wirelessUpFlow				OBJECT-TYPE
					SYNTAX     Counter64 
					MAX-ACCESS read-only
					STATUS     current
					DESCRIPTION
				        	"Wireless up flow."
					::= { dot11RadioStatisticsEntry 2 }

wirelessDownFlow			OBJECT-TYPE
					SYNTAX     Counter64 
					MAX-ACCESS read-only
					STATUS     current
					DESCRIPTION
				        	"Wireless down flow."
					::= { dot11RadioStatisticsEntry 3 }

channelDownAllPkts			OBJECT-TYPE
					SYNTAX     Counter64 
					MAX-ACCESS read-only
					STATUS     current
					DESCRIPTION
				        	"All the packets of down channel."
					::= { dot11RadioStatisticsEntry 4 }

channelDownAllDropPkts			OBJECT-TYPE
					SYNTAX     Counter64 
					MAX-ACCESS read-only
					STATUS     current
					DESCRIPTION
				        	"All the drop packets of down channel."
					::= { dot11RadioStatisticsEntry 5 }

channelDownAllMacErrPkts		OBJECT-TYPE
					SYNTAX     Counter64 
					MAX-ACCESS read-only
					STATUS     current
					DESCRIPTION
				        	"All the mac error packets of down channel."
					::= { dot11RadioStatisticsEntry 6 }

channelDownAllResPkts			OBJECT-TYPE
					SYNTAX     Counter64 
					MAX-ACCESS read-only
					STATUS     current
					DESCRIPTION
				        	"All the resend packets of down channel."
					::= { dot11RadioStatisticsEntry 7 }

channelUpAllFrames			OBJECT-TYPE
					SYNTAX     Counter64 
					MAX-ACCESS read-only
					STATUS     current
					DESCRIPTION
				        	"All the frames of up channel."
					::= { dot11RadioStatisticsEntry 8 }

channelDownAllFrames			OBJECT-TYPE
					SYNTAX     Counter64 
					MAX-ACCESS read-only
					STATUS     current
					DESCRIPTION
				        	"All the frames of down channel."
					::= { dot11RadioStatisticsEntry 9 }

channelDownAllErrFrames			OBJECT-TYPE
					SYNTAX     Counter64 
					MAX-ACCESS read-only
					STATUS     current
					DESCRIPTION
				        	"All the error frames of down channel."
					::= { dot11RadioStatisticsEntry 10 }

channelDownAllDropFrames		OBJECT-TYPE
					SYNTAX     Counter64 
					MAX-ACCESS read-only
					STATUS     current
					DESCRIPTION
				        	"All the drop frames of down channel."
					::= { dot11RadioStatisticsEntry 11 }

channelDownAllResFrames			OBJECT-TYPE
					SYNTAX     Counter64 
					MAX-ACCESS read-only
					STATUS     current
					DESCRIPTION
				        	"All the resend frames of down channel."
					::= { dot11RadioStatisticsEntry 12 }

channelUpAllDropFrames		OBJECT-TYPE
					SYNTAX     Counter64 
					MAX-ACCESS read-only
					STATUS     current
					DESCRIPTION
				        	"All the drop frames of up channel."
					::= { dot11RadioStatisticsEntry 13 }

channelUpAllResFrames			OBJECT-TYPE
					SYNTAX     Counter64 
					MAX-ACCESS read-only
					STATUS     current
					DESCRIPTION
				        	"All the resend frames of up channel."
					::= { dot11RadioStatisticsEntry 14 }
					
--**********************************************************************************************************
dot11RadioWlanTable OBJECT-TYPE
    SYNTAX      SEQUENCE OF Dot11RadioWlanEntry
    MAX-ACCESS  not-accessible
    STATUS      current
    DESCRIPTION
        "Radio bind WLAN information."
    ::= { wtpRadio 5 }

dot11RadioWlanEntry  OBJECT-TYPE
    SYNTAX      Dot11RadioWlanEntry
    MAX-ACCESS  not-accessible
    STATUS      current
    DESCRIPTION
        "Radio bind WLAN information."
    INDEX { wtpRadCurrID,
		BindWlanID }
    ::= { dot11RadioWlanTable 1 }
   
Dot11RadioWlanEntry ::=SEQUENCE{
	BindWlanID				INTEGER,
	TrafficLimitState			INTEGER,
	TrafficLimitValue			INTEGER,
	IsOnlyAllow11nStaAccess			TruthValue
}
BindWlanID				OBJECT-TYPE
					SYNTAX     INTEGER 
					MAX-ACCESS read-only
					STATUS     current
					DESCRIPTION
				        	"Radio bind WLAN ID."
					::= { dot11RadioWlanEntry 1 }

TrafficLimitState			OBJECT-TYPE
					SYNTAX     INTEGER{
							enable(1),
							disable(2)
							}
					MAX-ACCESS read-write
					STATUS     current
					DESCRIPTION
				        	"Traffic limit state."
					::= { dot11RadioWlanEntry 2 }					
					
TrafficLimitValue			OBJECT-TYPE
					SYNTAX     INTEGER
					MAX-ACCESS read-write
					STATUS     current
					DESCRIPTION
				        	"Traffic limit value."
					::= { dot11RadioWlanEntry 3 }	
					
IsOnlyAllow11nStaAccess			OBJECT-TYPE
					SYNTAX     TruthValue
					MAX-ACCESS read-write
					STATUS     current
					DESCRIPTION
				        	"Whether only allows 11N terminal access."
					::= { dot11RadioWlanEntry 4 }  									
					
--***********************************************************************************************************
dot11SSIDInfoTable OBJECT-TYPE
    SYNTAX      SEQUENCE OF Dot11SSIDInfoEntry
    MAX-ACCESS  not-accessible
    STATUS      current
    DESCRIPTION
        "This table shows SSID information."
    ::= { wtpWlan 4 }

dot11SSIDInfoEntry  OBJECT-TYPE
    SYNTAX      Dot11SSIDInfoEntry
    MAX-ACCESS  not-accessible
    STATUS      current
    DESCRIPTION
        "SSID information."
    INDEX { wtpMacAddr,
		wlanCurrID }
    ::= { dot11SSIDInfoTable 1 }
   
Dot11SSIDInfoEntry ::=SEQUENCE{
	wtpSSIDName		DisplayString,
	wtpSSIDMaxLoginUsr	INTEGER,
	wtpSSIDLoadBalance	INTEGER,
	wtpSSIDESSID		DisplayString,
	wtpSSIDState		INTEGER,
	wtpSSIDSecurityPolicyID	INTEGER
}
wtpSSIDName		OBJECT-TYPE
			SYNTAX     DisplayString
			MAX-ACCESS read-only
			STATUS     current
			DESCRIPTION
				"SSID name."
			::= { dot11SSIDInfoEntry 1 }

wtpSSIDMaxLoginUsr		OBJECT-TYPE
				SYNTAX     INTEGER(0..65535)
				MAX-ACCESS read-write
				STATUS     current
				DESCRIPTION
					"Max login user number.(Range 0-65535,if the input value larger than 65535,it will not be set)"
				::= { dot11SSIDInfoEntry 2 }

wtpSSIDLoadBalance		OBJECT-TYPE
				SYNTAX     INTEGER{
						enable(1),
						disable(0)
						}
				MAX-ACCESS read-only
				STATUS     current
				DESCRIPTION
					"Wlan load balancing state."
				::= { dot11SSIDInfoEntry 3 }

wtpSSIDESSID			OBJECT-TYPE
				SYNTAX     DisplayString
				MAX-ACCESS read-only
				STATUS     current
				DESCRIPTION
					"ESSID."
				::= { dot11SSIDInfoEntry 4 }

wtpSSIDState			OBJECT-TYPE
				SYNTAX     INTEGER{
						enable(1),
						disable(0)
						}
				MAX-ACCESS read-write
				STATUS     current
				DESCRIPTION
					"SSID state."
				::= { dot11SSIDInfoEntry 5 }

wtpSSIDSecurityPolicyID		OBJECT-TYPE
				SYNTAX     INTEGER
				MAX-ACCESS read-only
				STATUS     current
				DESCRIPTION
					"SSID security policy ID(0 means no security policy)."
				::= { dot11SSIDInfoEntry 6 }
dot11SecurityMechTable OBJECT-TYPE
	    SYNTAX      SEQUENCE OF Dot11SecurityMechEntry
	    MAX-ACCESS  not-accessible
	    STATUS      current
	    DESCRIPTION
	        "This table shows wireless security mechanism information."
	    ::= { wtpSecurity 1 }

dot11SecurityMechEntry  OBJECT-TYPE
    SYNTAX      Dot11SecurityMechEntry
    MAX-ACCESS  not-accessible
    STATUS      current
    DESCRIPTION
        "Wireless security mechanism information."
    INDEX { wtpMacAddr,
		wlanCurrID }
    ::= { dot11SecurityMechTable 1 }
   
Dot11SecurityMechEntry ::=SEQUENCE{
	wtpWirelessSecurMechName		DisplayString,
	wtpWirelessSecurMechID			INTEGER,
	wtpWirelessSecurMechType		DisplayString,
	wtpWirelessSecurMechEncryType		INTEGER,
	wtpWirelessSecurMechSecurPolicyKey	DisplayString,
	wtpWirelessSecurMechKeyInputType	DisplayString
	
}
wtpWirelessSecurMechName		OBJECT-TYPE
					SYNTAX     DisplayString
					MAX-ACCESS read-only
					STATUS     current
					DESCRIPTION
				        	"Security mechanism name."
					::= { dot11SecurityMechEntry 1 }


wtpWirelessSecurMechID			OBJECT-TYPE
					SYNTAX     INTEGER
					MAX-ACCESS read-write
					STATUS     current
					DESCRIPTION
				        	"Security mechanism ID."
					::= { dot11SecurityMechEntry 2 }

wtpWirelessSecurMechType		OBJECT-TYPE
					SYNTAX     DisplayString
					MAX-ACCESS read-only
					STATUS     current
					DESCRIPTION
				        	"Security mechanism type."
					::= { dot11SecurityMechEntry 3 }

wtpWirelessSecurMechEncryType		OBJECT-TYPE
					SYNTAX     INTEGER{
							NONE(0),
							WEP(1),
							AES(2),
							TKIP(3),
							SMS4(4)
							}
					MAX-ACCESS read-write
					STATUS     current
					DESCRIPTION
				        	"Security mechanism encryption type."
					::= { dot11SecurityMechEntry 4 }

wtpWirelessSecurMechSecurPolicyKey	OBJECT-TYPE
					SYNTAX     DisplayString
					MAX-ACCESS read-only
					STATUS     current
					DESCRIPTION
				        	"Security mechanism security policy key."
					::= { dot11SecurityMechEntry 5 }

wtpWirelessSecurMechKeyInputType	OBJECT-TYPE
					SYNTAX     DisplayString
					MAX-ACCESS read-only
					STATUS     current
					DESCRIPTION
				        	"Security mechanism key input type."
					::= { dot11SecurityMechEntry 6 }

dot11UsrLinkTable OBJECT-TYPE
	    SYNTAX      SEQUENCE OF Dot11UsrLinkEntry
	    MAX-ACCESS  not-accessible
	    STATUS      current
	    DESCRIPTION
	        "This table shows User link information."
	    ::= { wtpLink 1 }

dot11UsrLinkEntry  OBJECT-TYPE
    SYNTAX      Dot11UsrLinkEntry
    MAX-ACCESS  not-accessible
    STATUS      current
    DESCRIPTION
        "User link information."
    INDEX { wtpMacAddr }
    ::= { dot11UsrLinkTable 1 }
   
Dot11UsrLinkEntry ::=SEQUENCE{
	wtpReasonInvalidFailLinkTimes		Counter32,
	wtpReasonTimeOutFailLinkTimes		Counter32,
	wtpReasonRefuseFailLinkTimes		Counter32,
	wtpReasonOthersFailLinkTimes		Counter32,
	wtpSolutionLinksVerifyLinkTimes		Counter32,
	wtpReasonUsrLeaveVerfiyLinkTimes	Counter32,
	wtpReasonLackAbilityVerifyLinkTimes	Counter32,
	wtpReasonExceptionVerifyLinkTimes	Counter32,
	wtpReasonOtherVerfyLinkTimes		Counter32,
	wtpStaTotalOnlineTime			TimeTicks,
	wtpStaNewTotalOnlineTime		TimeTicks
}

wtpReasonInvalidFailLinkTimes		OBJECT-TYPE
					SYNTAX     Counter32
					MAX-ACCESS read-only
					STATUS     current
					DESCRIPTION
				        	"The total user link verification failed times because of invalided."
					::= { dot11UsrLinkEntry 1 }

wtpReasonTimeOutFailLinkTimes		OBJECT-TYPE
					SYNTAX     Counter32
					MAX-ACCESS read-only
					STATUS     current
					DESCRIPTION
				        	"The total user link verification failed times because of time out."
					::= { dot11UsrLinkEntry 2 }

wtpReasonRefuseFailLinkTimes		OBJECT-TYPE
					SYNTAX     Counter32
					MAX-ACCESS read-only
					STATUS     current
					DESCRIPTION
				        	"The total user link verification failed times because of refusing."
					::= { dot11UsrLinkEntry 3 }

wtpReasonOthersFailLinkTimes		OBJECT-TYPE
					SYNTAX     Counter32
					MAX-ACCESS read-only
					STATUS     current
					DESCRIPTION
				        	"The total user link verification failed times because of other reasons."
					::= { dot11UsrLinkEntry 4 }

wtpSolutionLinksVerifyLinkTimes		OBJECT-TYPE
					SYNTAX     Counter32
					MAX-ACCESS read-only
					STATUS     current
					DESCRIPTION
				        	"The total times that solution link verfication."
					::= { dot11UsrLinkEntry 5 }

wtpReasonUsrLeaveVerfiyLinkTimes	OBJECT-TYPE
					SYNTAX     Counter32
					MAX-ACCESS read-only
					STATUS     current
					DESCRIPTION
				        	"The total times that solution link verfication because of user leaving."
					::= { dot11UsrLinkEntry 6 }

wtpReasonLackAbilityVerifyLinkTimes	OBJECT-TYPE
					SYNTAX     Counter32
					MAX-ACCESS read-only
					STATUS     current
					DESCRIPTION
				        	"The total times that solution link verfication because of lack of ability."
					::= { dot11UsrLinkEntry 7 }

wtpReasonExceptionVerifyLinkTimes	OBJECT-TYPE
					SYNTAX     Counter32
					MAX-ACCESS read-only
					STATUS     current
					DESCRIPTION
				        	"The total times that solution link verfication because of exception."
					::= { dot11UsrLinkEntry 8 }

wtpReasonOtherVerfyLinkTimes		OBJECT-TYPE
					SYNTAX     Counter32
					MAX-ACCESS read-only
					STATUS     current
					DESCRIPTION
				        	"The total times that solution link verfication because of other reason."
					::= { dot11UsrLinkEntry 9 }
wtpStaTotalOnlineTime			OBJECT-TYPE
					SYNTAX     TimeTicks
					MAX-ACCESS read-only
					STATUS     current
					DESCRIPTION
				        	"The total station online time on the AP ."
					::= { dot11UsrLinkEntry 10 }
					
wtpStaNewTotalOnlineTime		OBJECT-TYPE
					SYNTAX     TimeTicks
					MAX-ACCESS read-only
					STATUS     current
					DESCRIPTION
				        	"The total station online time on the AP, the time is not cleared if AP restart."
					::= { dot11UsrLinkEntry 11 }
					
										
dot11ConjunctionTable OBJECT-TYPE
	    SYNTAX      SEQUENCE OF Dot11ConjunctionEntry
	    MAX-ACCESS  not-accessible
	    STATUS      current
	    DESCRIPTION
	        "This table shows Conjunction information."
	    ::= { wtpLink 2 }

dot11ConjunctionEntry  OBJECT-TYPE
    SYNTAX      Dot11ConjunctionEntry
    MAX-ACCESS  not-accessible
    STATUS      current
    DESCRIPTION
        "Conjunction information."
    INDEX { wtpMacAddr }
    ::= { dot11ConjunctionTable 1 }
   
Dot11ConjunctionEntry ::=SEQUENCE{
	wtpReasonInvalidFailConjunctTimes		Counter32,
	wtpReasonTimeOutFailConjunctTimes		Counter32,
	wtpReasonRefuseFailConjunctTimes		Counter32,
	wtpReasonOthersFailConjunctTimes		Counter32,
	wtpTryReconjunctTimes				Counter32,
	wtpReconjunctSuccessTimes			Counter32,
	wtpReasonInvalidReconjunctTimes			Counter32,
	wtpReasonTimeOutReconjunctTimes			Counter32,
	wtpReasonRefuseReconjunctTimes			Counter32,
	wtpReasonOtherReconjunctTimes			Counter32,
	wtpSolutionConjunctTimes			Counter32,
	wtpReasonUsrLeaveSolutionConjunctTimes		Counter32,
	wtpReasonLackAbilitySolutionConjunctTimes	Counter32,
	wtpReasonExceptionSolutionConjunctTimes		Counter32,
	wtpReasonOtherSolutionConjunctTimes		Counter32,
	wtpReasonTerminalNotSupportAllSpeedFailConjunctionTimes		Counter32,
	wtpNotContainedInStdReasonAssocFailSum		Counter32,
	wtpUnknowReasonAssocFailSum			Counter32,
	wtpPreAssCannotShiftDeassocFailSum		Counter32
	
}
wtpReasonInvalidFailConjunctTimes	OBJECT-TYPE
					SYNTAX     Counter32
					MAX-ACCESS read-only
					STATUS     current
					DESCRIPTION
				        	"The total user conjunction failed times because of invalided."
					::= { dot11ConjunctionEntry 1 }

wtpReasonTimeOutFailConjunctTimes	OBJECT-TYPE
					SYNTAX     Counter32
					MAX-ACCESS read-only
					STATUS     current
					DESCRIPTION
				        	"The total user conjunction failed times because of time out."
					::= { dot11ConjunctionEntry 2 }

wtpReasonRefuseFailConjunctTimes		OBJECT-TYPE
					SYNTAX     Counter32
					MAX-ACCESS read-only
					STATUS     current
					DESCRIPTION
				        	"The total user conjunction failed times because of refusing."
					::= { dot11ConjunctionEntry 3 }

wtpReasonOthersFailConjunctTimes		OBJECT-TYPE
					SYNTAX     Counter32
					MAX-ACCESS read-only
					STATUS     current
					DESCRIPTION
				        	"The total user conjunction failed times because of other reason."
					::= { dot11ConjunctionEntry 4 }

wtpTryReconjunctTimes			OBJECT-TYPE
					SYNTAX     Counter32
					MAX-ACCESS read-only
					STATUS     current
					DESCRIPTION
				        	"The total times that try to reconjunction."
					::= { dot11ConjunctionEntry 5 }

wtpReconjunctSuccessTimes		OBJECT-TYPE
					SYNTAX     Counter32
					MAX-ACCESS read-only
					STATUS     current
					DESCRIPTION
				        	"The total successful times that reconjunction."
					::= { dot11ConjunctionEntry 6 }

wtpReasonInvalidReconjunctTimes		OBJECT-TYPE
					SYNTAX     Counter32
					MAX-ACCESS read-only
					STATUS     current
					DESCRIPTION
				        	"The total user reconjunction failed times because of invalided."
					::= { dot11ConjunctionEntry 7 }

wtpReasonTimeOutReconjunctTimes		OBJECT-TYPE
					SYNTAX     Counter32
					MAX-ACCESS read-only
					STATUS     current
					DESCRIPTION
				        	"The total user reconjunction failed times because of time out."
					::= { dot11ConjunctionEntry 8 }

wtpReasonRefuseReconjunctTimes		OBJECT-TYPE
					SYNTAX     Counter32
					MAX-ACCESS read-only
					STATUS     current
					DESCRIPTION
				        	"The total user reconjunction failed times because of refusing."
					::= { dot11ConjunctionEntry 9 }

wtpReasonOtherReconjunctTimes		OBJECT-TYPE
					SYNTAX     Counter32
					MAX-ACCESS read-only
					STATUS     current
					DESCRIPTION
				        	"The total user reconjunction failed times because of other reasons."
					::= { dot11ConjunctionEntry 10 }

wtpSolutionConjunctTimes			OBJECT-TYPE
					SYNTAX     Counter32
					MAX-ACCESS read-only
					STATUS     current
					DESCRIPTION
				        	"The total times that solution Conjunct"
					::= { dot11ConjunctionEntry 11 }

wtpReasonUsrLeaveSolutionConjunctTimes	OBJECT-TYPE
					SYNTAX     Counter32
					MAX-ACCESS read-only
					STATUS     current
					DESCRIPTION
				        	"The total times that solution conjunction because of user leaving."
					::= { dot11ConjunctionEntry 12 }

wtpReasonLackAbilitySolutionConjunctTimes	OBJECT-TYPE
					SYNTAX     Counter32
					MAX-ACCESS read-only
					STATUS     current
					DESCRIPTION
				        	"The total times that solution conjunction because of lack of ablility."
					::= { dot11ConjunctionEntry 13 }

wtpReasonExceptionSolutionConjunctTimes	OBJECT-TYPE
					SYNTAX     Counter32
					MAX-ACCESS read-only
					STATUS     current
					DESCRIPTION
				        	"The total times that solution conjunction because of excertion."
					::= { dot11ConjunctionEntry 14 }

wtpReasonOtherSolutionConjunctTimes	OBJECT-TYPE
					SYNTAX     Counter32
					MAX-ACCESS read-only
					STATUS     current
					DESCRIPTION
				        	"The total times that solution conjunction because of other reasons."
					::= { dot11ConjunctionEntry 15 }

wtpReasonTerminalNotSupportAllSpeedFailConjunctionTimes		OBJECT-TYPE
								SYNTAX     Counter32
								MAX-ACCESS read-only
								STATUS     current
								DESCRIPTION
							        	"The total times that fail conjunction because of not support all the speed."
								::= { dot11ConjunctionEntry 16 }

wtpNotContainedInStdReasonAssocFailSum		OBJECT-TYPE
						SYNTAX     Counter32
						MAX-ACCESS read-only
						STATUS     current
						DESCRIPTION
						      	"The total times that fail conjunction because of not in the standard of 802.11."
						::= { dot11ConjunctionEntry 17 }

wtpUnknowReasonAssocFailSum			OBJECT-TYPE
						SYNTAX     Counter32
						MAX-ACCESS read-only
						STATUS     current
						DESCRIPTION
						       	"The total times that fail conjunction because of unknown reason."
						::= { dot11ConjunctionEntry 18 }

wtpPreAssCannotShiftDeassocFailSum		OBJECT-TYPE
						SYNTAX     Counter32
						MAX-ACCESS read-only
						STATUS     current
						DESCRIPTION
						       	"The total times that fail conjunction because of unknown."
						::= { dot11ConjunctionEntry 19 }

dot11DistinguishTable OBJECT-TYPE
	    SYNTAX      SEQUENCE OF Dot11DistinguishEntry
	    MAX-ACCESS  not-accessible
	    STATUS      current
	    DESCRIPTION
	        "This table shows user Distinguish information."
	    ::= { wtpLink 3 }

dot11DistinguishEntry  OBJECT-TYPE
    SYNTAX      Dot11DistinguishEntry
    MAX-ACCESS  not-accessible
    STATUS      current
    DESCRIPTION
        "User distinguish information."
    INDEX { wtpMacAddr }
    ::= { dot11DistinguishTable 1 }
   
Dot11DistinguishEntry ::=SEQUENCE{
	wtpTryDistinguishTimes			Counter32,
	wtpDistinguishSuccessTimes		Counter32,
	wtpReasonErrKeyFailDistinguishTimes	Counter32,
	wtpReasonInvalidFailDistinguishTimes	Counter32,
	wtpReasonTimeOutFailDistinguishTimes	Counter32,
	wtpReasonRefuseFailDistinguishTimes	Counter32,
	wtpReasonOthersFailDistinguishTimes	Counter32,
	wtpUserRequestTimes			Counter32,
	wtpAssociatedUserNum			Counter32
}
wtpTryDistinguishTimes			OBJECT-TYPE
					SYNTAX     Counter32
					MAX-ACCESS read-only
					STATUS     current
					DESCRIPTION
				        	"The total times that trying to distinguish."
					::= { dot11DistinguishEntry 1 }

wtpDistinguishSuccessTimes		OBJECT-TYPE
					SYNTAX     Counter32
					MAX-ACCESS read-only
					STATUS     current
					DESCRIPTION
				        	"The total times that distinguish successfully."
					::= { dot11DistinguishEntry 2 }

wtpReasonErrKeyFailDistinguishTimes	OBJECT-TYPE
					SYNTAX     Counter32
					MAX-ACCESS read-only
					STATUS     current
					DESCRIPTION
				        	"The total times that distinguish failed because of wrong key."
					::= { dot11DistinguishEntry 3 }

wtpReasonInvalidFailDistinguishTimes	OBJECT-TYPE
					SYNTAX     Counter32
					MAX-ACCESS read-only
					STATUS     current
					DESCRIPTION
				        	"The total times that distinguish failed because of invalided."
					::= { dot11DistinguishEntry 4 }

wtpReasonTimeOutFailDistinguishTimes	OBJECT-TYPE
					SYNTAX     Counter32
					MAX-ACCESS read-only
					STATUS     current
					DESCRIPTION
				        	"The total times that distinguish failed because of time out."
					::= { dot11DistinguishEntry 5 }

wtpReasonRefuseFailDistinguishTimes	OBJECT-TYPE
					SYNTAX     Counter32
					MAX-ACCESS read-only
					STATUS     current
					DESCRIPTION
				        	"The total times that distinguish failed because of refusing."
					::= { dot11DistinguishEntry 6 }

wtpReasonOthersFailDistinguishTimes	OBJECT-TYPE
					SYNTAX     Counter32
					MAX-ACCESS read-only
					STATUS     current
					DESCRIPTION
				        	"The total times that distinguish failed because of other reasons."
					::= { dot11DistinguishEntry 7 }
					
wtpUserRequestTimes			OBJECT-TYPE
					SYNTAX     Counter32
					MAX-ACCESS read-only
					STATUS     current
					DESCRIPTION
				        	"The total request times of user."
					::= { dot11DistinguishEntry 8 }
					
wtpAssociatedUserNum			OBJECT-TYPE
					SYNTAX  Counter32
					MAX-ACCESS read-only
					STATUS     current
					DESCRIPTION
						"The number of users associated."
					::= { dot11DistinguishEntry 9 }						


					
dot11VlanAbilityTable OBJECT-TYPE
	    SYNTAX      SEQUENCE OF Dot11VlanAbilityEntry
	    MAX-ACCESS  not-accessible
	    STATUS      current
	    DESCRIPTION
	        "This table shows vlan ability information."
	    ::= { wtpWlan 5 }

dot11VlanAbilityEntry  OBJECT-TYPE
    SYNTAX      Dot11VlanAbilityEntry
    MAX-ACCESS  not-accessible
    STATUS      current
    DESCRIPTION
        "Vlan ability information."
    INDEX { wtpMacAddr,
		wlanCurrID }
    ::= { dot11VlanAbilityTable 1 }
   
Dot11VlanAbilityEntry ::=SEQUENCE{
	vlanID			INTEGER,
	Priority		INTEGER
}
vlanID		OBJECT-TYPE
		SYNTAX  INTEGER
		MAX-ACCESS read-write
		STATUS     current
		DESCRIPTION
			"Vlan ID."
			::= { dot11VlanAbilityEntry 1 }

Priority	OBJECT-TYPE
		SYNTAX  INTEGER
		MAX-ACCESS read-write
		STATUS     current
		DESCRIPTION
			"Priority."
			::= { dot11VlanAbilityEntry 2 }
dot11SSIDStatsTable OBJECT-TYPE
	    SYNTAX      SEQUENCE OF Dot11SSIDStatsEntry
	    MAX-ACCESS  not-accessible
	    STATUS      current
	    DESCRIPTION
	        "This table shows SSID stats information."
	    ::= { wtpWlan 6 }

dot11SSIDStatsEntry  OBJECT-TYPE
    SYNTAX      Dot11SSIDStatsEntry
    MAX-ACCESS  not-accessible
    STATUS      current
    DESCRIPTION
        "SSID stats information."
    INDEX { wtpMacAddr,
		wlanCurrID }
    ::= { dot11SSIDStatsTable 1 }
   
Dot11SSIDStatsEntry ::=SEQUENCE{
		SSIDTxSignalPkts			Counter32,
		SSIDRxSignalPkts			Counter32,
		SSIDTxDataPkts				Counter32,
		SSIDRxDataPkts				Counter32,
		SSIDUplinkDataOctets			Counter64,
		SSIDDwlinkDataOctets			Counter64,
		SSIDChStatsDwlinkTotRetryPkts		Counter32,
		SSIDChStatsUplinkUniFrameCnt		Counter32,
		SSIDChStatsDwlinkUniFrameCnt		Counter32,
		SSIDUpChStatsFrameNonUniFrameCnt	Counter32,
		SSIDDownChStatsFrameNonUniFrameCnt	Counter32,
		SSIDApChStatsFrameFragRate		Counter32,
		SSIDRxCtrlFrameCnt			Counter32,
		SSIDRxDataFrameCnt			Counter32,
		SSIDRxAuthenFrameCnt			Counter32,
		SSIDRxAssociateFrameCnt			Counter32,
		SSIDTxCtrlFrameCnt			Counter32,
		SSIDTxDataFrameCnt			Counter32,
		SSIDTxAuthenFrameCnt			Counter32,
		SSIDTxAssociateFrameCnt			Counter32,
		SSIDApChStatsNumStations		Counter32,
		SSIDDwlinkTotFrameCnt			Counter32,
		SSIDUplinkTotFrameCnt			Counter32,
		SSIDAssociatedUserNum			Counter32
}
SSIDTxSignalPkts		OBJECT-TYPE
				SYNTAX  Counter32
				MAX-ACCESS read-only
				STATUS     current
				DESCRIPTION
					"The total number of transmitted signaling packet."
				::= { dot11SSIDStatsEntry 1 }

SSIDRxSignalPkts		OBJECT-TYPE
				SYNTAX  Counter32
				MAX-ACCESS read-only
				STATUS     current
				DESCRIPTION
					"The total number of received signaling packet."
				::= { dot11SSIDStatsEntry 2 }

SSIDTxDataPkts			OBJECT-TYPE
				SYNTAX  Counter32
				MAX-ACCESS read-only
				STATUS     current
				DESCRIPTION
					"The total number of transmitted data packet."
				::= { dot11SSIDStatsEntry 3 }

SSIDRxDataPkts			OBJECT-TYPE
				SYNTAX  Counter32
				MAX-ACCESS read-only
				STATUS     current
				DESCRIPTION
					"The total number of received signaling packet."
				::= { dot11SSIDStatsEntry 4 }

SSIDUplinkDataOctets		OBJECT-TYPE
				SYNTAX  Counter64
				MAX-ACCESS read-only
				STATUS     current
				DESCRIPTION
					"Number of bytes received."
				::= { dot11SSIDStatsEntry 5 }

SSIDDwlinkDataOctets		OBJECT-TYPE
				SYNTAX  Counter64
				MAX-ACCESS read-only
				STATUS     current
				DESCRIPTION
					"Number of bytes sent."
				::= { dot11SSIDStatsEntry 6 }

SSIDChStatsDwlinkTotRetryPkts	OBJECT-TYPE
				SYNTAX  Counter32
				MAX-ACCESS read-only
				STATUS     current
				DESCRIPTION
					"Downlink packet retransmission number."
				::= { dot11SSIDStatsEntry 7 }

SSIDChStatsUplinkUniFrameCnt	OBJECT-TYPE
				SYNTAX  Counter32
				MAX-ACCESS read-only
				STATUS     current
				DESCRIPTION
					"Uplink unicast frames."
				::= { dot11SSIDStatsEntry 8 }

SSIDChStatsDwlinkUniFrameCnt	OBJECT-TYPE
				SYNTAX  Counter32
				MAX-ACCESS read-only
				STATUS     current
				DESCRIPTION
					"Downlink unicast frames."
				::= { dot11SSIDStatsEntry 9 }

SSIDUpChStatsFrameNonUniFrameCnt	OBJECT-TYPE
				SYNTAX  Counter32
				MAX-ACCESS read-only
				STATUS     current
				DESCRIPTION
					"Uplink unicast frames."
				::= { dot11SSIDStatsEntry 10 }

SSIDDownChStatsFrameNonUniFrameCnt	OBJECT-TYPE
				SYNTAX  Counter32
				MAX-ACCESS read-only
				STATUS     current
				DESCRIPTION
					"Downlink unicast frames."
				::= { dot11SSIDStatsEntry 11 }

SSIDApChStatsFrameFragRate	OBJECT-TYPE
				SYNTAX  Counter32
				MAX-ACCESS read-only
				STATUS     current
				DESCRIPTION
					"Sub-frame rate."
				::= { dot11SSIDStatsEntry 12 }

SSIDRxCtrlFrameCnt		OBJECT-TYPE
				SYNTAX  Counter32
				MAX-ACCESS read-only
				STATUS     current
				DESCRIPTION
					"Received the number of control frames."
				::= { dot11SSIDStatsEntry 13 }

SSIDRxDataFrameCnt		OBJECT-TYPE
				SYNTAX  Counter32
				MAX-ACCESS read-only
				STATUS     current
				DESCRIPTION
					"Received the number of data frames."
				::= { dot11SSIDStatsEntry 14 }

SSIDRxAuthenFrameCnt		OBJECT-TYPE
				SYNTAX  Counter32
				MAX-ACCESS read-only
				STATUS     current
				DESCRIPTION
					"Received certification of the number of frames."
				::= { dot11SSIDStatsEntry 15 }

SSIDRxAssociateFrameCnt		OBJECT-TYPE
				SYNTAX  Counter32
				MAX-ACCESS read-only
				STATUS     current
				DESCRIPTION
					"Received the number of frames associated."
				::= { dot11SSIDStatsEntry 16 }

SSIDTxCtrlFrameCnt		OBJECT-TYPE
				SYNTAX  Counter32
				MAX-ACCESS read-only
				STATUS     current
				DESCRIPTION
					"Send the number of control frames."
				::= { dot11SSIDStatsEntry 17 }

SSIDTxDataFrameCnt		OBJECT-TYPE
				SYNTAX  Counter32
				MAX-ACCESS read-only
				STATUS     current
				DESCRIPTION
					"Sent the number of data frames."
				::= { dot11SSIDStatsEntry 18 }

SSIDTxAuthenFrameCnt		OBJECT-TYPE
				SYNTAX  Counter32
				MAX-ACCESS read-only
				STATUS     current
				DESCRIPTION
					"Send the number of frames of the certification."
				::= { dot11SSIDStatsEntry 19 }

SSIDTxAssociateFrameCnt		OBJECT-TYPE
				SYNTAX  Counter32
				MAX-ACCESS read-only
				STATUS     current
				DESCRIPTION
					"Send the link of the number of frames."
				::= { dot11SSIDStatsEntry 20 }

SSIDApChStatsNumStations	OBJECT-TYPE
				SYNTAX  Counter32
				MAX-ACCESS read-only
				STATUS     current
				DESCRIPTION
					"Current SSID to connect to the terminal number."
				::= { dot11SSIDStatsEntry 21 }
				
SSIDDwlinkTotFrameCnt		OBJECT-TYPE
				SYNTAX  Counter32
				MAX-ACCESS read-only
				STATUS     current
				DESCRIPTION
					"SSID DOWN TOTLE of frames."
				::= { dot11SSIDStatsEntry 22 }
SSIDUplinkTotFrameCnt		OBJECT-TYPE
				SYNTAX  Counter32
				MAX-ACCESS read-only
				STATUS     current
				DESCRIPTION
					"SSID UP TOTLE of frames."
				::= { dot11SSIDStatsEntry 23 }
				
SSIDAssociatedUserNum		OBJECT-TYPE
				SYNTAX  Counter32
				MAX-ACCESS read-only
				STATUS     current
				DESCRIPTION
					"SSID associated user num."
				::= { dot11SSIDStatsEntry 24 }	
							
		
dot11SSIDExternStatsTable OBJECT-TYPE
	    SYNTAX      SEQUENCE OF Dot11SSIDExternStatsEntry
	    MAX-ACCESS  not-accessible
	    STATUS      current
	    DESCRIPTION
	        "This table shows SSID stats information."
	    ::= { wtpWlan 7 }
dot11SSIDExternStatsEntry  OBJECT-TYPE
    SYNTAX      Dot11SSIDExternStatsEntry
    MAX-ACCESS  not-accessible
    STATUS      current
    DESCRIPTION
        "SSID stats information."
    INDEX { wtpMacAddr,
		wlanCurrID }
    ::= { dot11SSIDExternStatsTable 1 }
   
Dot11SSIDExternStatsEntry ::=SEQUENCE{
		SSIDDwErrPkts				Counter32,
		SSIDDwDropPkts				Counter32,
		SSIDDwTotErrFrames			Counter32,
		SSIDUpErrPkts				Counter32,
		SSIDUpDropPkts				Counter32,
		SSIDUpTotErrFrames			Counter32
}
SSIDDwErrPkts			OBJECT-TYPE
				SYNTAX  Counter32
				MAX-ACCESS read-only
				STATUS     current
				DESCRIPTION
					"The total number of down error packet."
				::= { dot11SSIDExternStatsEntry 1 }
SSIDDwDropPkts			OBJECT-TYPE
				SYNTAX  Counter32
				MAX-ACCESS read-only
				STATUS     current
				DESCRIPTION
					"The total number of down drop  packet."
				::= { dot11SSIDExternStatsEntry 2 }
SSIDDwTotErrFrames		OBJECT-TYPE
				SYNTAX  Counter32
				MAX-ACCESS read-only
				STATUS     current
				DESCRIPTION
					"The total number of down err frames."
				::= { dot11SSIDExternStatsEntry 3 }
SSIDUpErrPkts			OBJECT-TYPE
				SYNTAX  Counter32
				MAX-ACCESS read-only
				STATUS     current
				DESCRIPTION
					"The total number of up error packet."
				::= { dot11SSIDExternStatsEntry 4 }
SSIDUpDropPkts			OBJECT-TYPE
				SYNTAX  Counter32
				MAX-ACCESS read-only
				STATUS     current
				DESCRIPTION
					"The total number of up drop packet."
				::= { dot11SSIDExternStatsEntry 5 }
SSIDUpTotErrFrames		OBJECT-TYPE
				SYNTAX  Counter32
				MAX-ACCESS read-only
				STATUS     current
				DESCRIPTION
					"The total number of up error frames."
				::= { dot11SSIDExternStatsEntry 6 }
dot11SSIDRateStatsTable OBJECT-TYPE
	    SYNTAX      SEQUENCE OF Dot11SSIDRateStatsEntry
	    MAX-ACCESS  not-accessible
	    STATUS      current
	    DESCRIPTION
	        "This table shows SSID stats information."
	    ::= { wtpWlan 8 }
dot11SSIDRateStatsEntry  OBJECT-TYPE
    SYNTAX      Dot11SSIDRateStatsEntry
    MAX-ACCESS  not-accessible
    STATUS      current
    DESCRIPTION
        "SSID stats information."
    INDEX { wtpMacAddr,
		wlanCurrID }
    ::= { dot11SSIDRateStatsTable 1 }
   
Dot11SSIDRateStatsEntry ::=SEQUENCE{
		SSIDInDropRate				DisplayString,
		SSIDOutDropRate				DisplayString,
		SSIDDownBandWidthRate			DisplayString,
		SSIDUpBandWidthRate			DisplayString
}
SSIDInDropRate			OBJECT-TYPE
				SYNTAX  DisplayString
				MAX-ACCESS read-only
				STATUS     current
				DESCRIPTION
					"The total number of in Drop Rate."
				::= { dot11SSIDRateStatsEntry 1 }
SSIDOutDropRate			OBJECT-TYPE
				SYNTAX  DisplayString
				MAX-ACCESS read-only
				STATUS     current
				DESCRIPTION
					"The total number of out drop  Rate."
				::= { dot11SSIDRateStatsEntry 2 }
SSIDDownBandWidthRate		OBJECT-TYPE
				SYNTAX  DisplayString
				MAX-ACCESS read-only
				STATUS     current
				DESCRIPTION
					"The total number of Down BandWidth Rate ."
				::= { dot11SSIDRateStatsEntry 3 }
SSIDUpBandWidthRate			OBJECT-TYPE
				SYNTAX  DisplayString
				MAX-ACCESS read-only
				STATUS     current
				DESCRIPTION
					"The total number of up BandWidth Rate ."
				::= { dot11SSIDRateStatsEntry 4 }


--***********************************************************************************
dot11WtpDeviceInfoTable OBJECT-TYPE
	    SYNTAX      SEQUENCE OF Dot11WtpDeviceInfoEntry
	    MAX-ACCESS  not-accessible
	    STATUS      current
	    DESCRIPTION
	        "This table shows device information,such as CPU,Flash,Memory."
	    ::= { wtpGeneralInfo 2 }

dot11WtpDeviceInfoEntry  OBJECT-TYPE
    SYNTAX      Dot11WtpDeviceInfoEntry
    MAX-ACCESS  not-accessible
    STATUS      current
    DESCRIPTION
        "Device information."
    INDEX { wtpMacAddr }
    ::= { dot11WtpDeviceInfoTable 1 }
Dot11WtpDeviceInfoEntry ::=SEQUENCE{
	wtpCPUType				DisplayString,
	wtpCPUProcessAbility			DisplayString,
	wtpCPURTUsage				INTEGER,
	wtpCPUPeakUsage				DisplayString,
	wtpCPUAvgUsage				INTEGER,
	wtpCPUusageThreshhd			INTEGER,
	wtpMemoryType				DisplayString,
	wtpMemoryCapacity			Gauge32,
	wtpMemRTUsage				INTEGER,
	wtpMemPeakUsage				DisplayString,
	wtpMemAvgUsage				INTEGER,
	wtpMemUsageThreshhd			INTEGER,
	wtpFlashType				DisplayString,
	wtpFlashCapacity  			INTEGER,
	wtpFlashRemain				INTEGER,
	wtpWayGetIP				INTEGER,
	wtpWorkTemp				DisplayString,
	wtpIP					IpAddress,
	wtpIpv6Address				InetAddressIPv6
}
wtpCPUType	 			OBJECT-TYPE
					SYNTAX     	DisplayString 
					MAX-ACCESS 	read-only
					STATUS     	current
					DESCRIPTION
				        	"AP CPU type."
					::= { dot11WtpDeviceInfoEntry 1 }

wtpCPUProcessAbility 			OBJECT-TYPE
					SYNTAX     DisplayString 
					MAX-ACCESS read-only
					STATUS     current
					DESCRIPTION
				        	"The CPU process ability."
					::= { dot11WtpDeviceInfoEntry 2 }

wtpCPURTUsage				OBJECT-TYPE
					SYNTAX     	INTEGER 
					MAX-ACCESS 	read-only
					STATUS     	current
					DESCRIPTION
				        	"AP's CPU use rate."
					::= { dot11WtpDeviceInfoEntry 3 }

wtpCPUPeakUsage				OBJECT-TYPE
					SYNTAX     	DisplayString 
					MAX-ACCESS 	read-only
					STATUS     	current
					DESCRIPTION
				        	"AP's CPU peak use rate."
					::= { dot11WtpDeviceInfoEntry 4 }

wtpCPUAvgUsage				OBJECT-TYPE
					SYNTAX     	INTEGER 
					MAX-ACCESS 	read-only
					STATUS     	current
					DESCRIPTION
				        	"AP's CPU average use rate."
					::= { dot11WtpDeviceInfoEntry 5 }

wtpCPUusageThreshhd			OBJECT-TYPE
					SYNTAX     INTEGER 
					MAX-ACCESS read-write
					STATUS     current
					DESCRIPTION
				        	"If CPU use rate too high,send trap."
					::= { dot11WtpDeviceInfoEntry 6 }

wtpMemoryType	 			OBJECT-TYPE
					SYNTAX     DisplayString 
					MAX-ACCESS read-only
					STATUS     current
					DESCRIPTION
				        	"The memory type."
					::= { dot11WtpDeviceInfoEntry 7 }

wtpMemoryCapacity 			OBJECT-TYPE
					SYNTAX     Gauge32 
					MAX-ACCESS read-only
					STATUS     current
					DESCRIPTION
				        	"The memory capacity(units KB)."
					::= { dot11WtpDeviceInfoEntry 8 }

wtpMemRTUsage			 	OBJECT-TYPE
					SYNTAX     INTEGER 
					MAX-ACCESS read-only
					STATUS     current
					DESCRIPTION
				        	"Memory current use rate."
					::= { dot11WtpDeviceInfoEntry 9 }

wtpMemPeakUsage				OBJECT-TYPE
					SYNTAX     DisplayString 
					MAX-ACCESS read-only
					STATUS     current
					DESCRIPTION
				        	"Memory peak use rate."
					::= { dot11WtpDeviceInfoEntry 10 }

wtpMemAvgUsage				OBJECT-TYPE
					SYNTAX     INTEGER 
					MAX-ACCESS read-only
					STATUS     current
					DESCRIPTION
				        	"Memory average use rate."
					::= { dot11WtpDeviceInfoEntry 11 }

wtpMemUsageThreshhd			OBJECT-TYPE
					SYNTAX     INTEGER
					MAX-ACCESS read-write
					STATUS     current
					DESCRIPTION
				        	"If memory use rate too high ,send trap."
					::= { dot11WtpDeviceInfoEntry 12 }

wtpFlashType		 		OBJECT-TYPE
					SYNTAX     DisplayString
					MAX-ACCESS read-only
					STATUS     current
					DESCRIPTION
				        	"Flash type."
					::= { dot11WtpDeviceInfoEntry 13 }

wtpFlashCapacity		 	OBJECT-TYPE
					SYNTAX     INTEGER
					UNITS	   "MB"
					MAX-ACCESS read-only
					STATUS     current
					DESCRIPTION
				        	"Flash Capacity(units KB)."
					::= { dot11WtpDeviceInfoEntry 14 }

wtpFlashRemain			 	OBJECT-TYPE
					SYNTAX     INTEGER
					UNITS	   "KB"
					MAX-ACCESS read-only
					STATUS     current
					DESCRIPTION
				        	"Flash surplus capacity(units KB)."
					::= { dot11WtpDeviceInfoEntry 15 }

wtpWayGetIP			 	OBJECT-TYPE
					SYNTAX     INTEGER{
						staticAllocation(0),
						DHCP(1),						
						PPPoE(2),
						DHCPv6(3),
						SLACC(4)
							} 
					MAX-ACCESS read-only
					STATUS     current
					DESCRIPTION
				        	"How ap get the IP."
					::= { dot11WtpDeviceInfoEntry 16 }

wtpWorkTemp			 	OBJECT-TYPE
					SYNTAX     DisplayString
					MAX-ACCESS read-only
					STATUS     current
					DESCRIPTION
				        	"Working temperature."
					::= { dot11WtpDeviceInfoEntry 17 }

wtpIP	 				OBJECT-TYPE
					SYNTAX     IpAddress 
					MAX-ACCESS read-only
					STATUS     current
					DESCRIPTION
				        	"AP IP address."
					::= { dot11WtpDeviceInfoEntry 18 }
wtpIpv6Address	 			OBJECT-TYPE
					SYNTAX     InetAddressIPv6 
					MAX-ACCESS read-only
					STATUS     current
					DESCRIPTION
				        	"AP IPv6 address."
					::= { dot11WtpDeviceInfoEntry 19 }
--****************************************file operation*************************************
dot11WtpConfigFileUpdateTable OBJECT-TYPE
	    SYNTAX      SEQUENCE OF Dot11WtpConfigFileUpdateEntry
	    MAX-ACCESS  not-accessible
	    STATUS      current
	    DESCRIPTION
	        "This table shows file operation config file."
	    ::= { wtpGeneralInfo 3 }

dot11WtpConfigFileUpdateEntry  OBJECT-TYPE
    SYNTAX      Dot11WtpConfigFileUpdateEntry
    MAX-ACCESS  not-accessible
    STATUS      current
    DESCRIPTION
        "This table shows file operation config file."
    INDEX { wtpMacAddr }
    ::= { dot11WtpConfigFileUpdateTable 1 }
Dot11WtpConfigFileUpdateEntry ::=SEQUENCE{
	wtpConfigFileUpdate		DisplayString
}
wtpConfigFileUpdate			OBJECT-TYPE
					SYNTAX     DisplayString
					MAX-ACCESS read-write
					STATUS     current
					DESCRIPTION
				        	"Config file update."
					::= { dot11WtpConfigFileUpdateEntry 1 }
--********************************************************************************************************
dot11WtpVersionFileUpdateTable OBJECT-TYPE
	    SYNTAX      SEQUENCE OF Dot11WtpVersionFileUpdateEntry
	    MAX-ACCESS  not-accessible
	    STATUS      current
	    DESCRIPTION
	        "This table shows file operation Version file."
	    ::= { wtpGeneralInfo 4 }

dot11WtpVersionFileUpdateEntry  OBJECT-TYPE
    SYNTAX      Dot11WtpVersionFileUpdateEntry
    MAX-ACCESS  not-accessible
    STATUS      current
    DESCRIPTION
        "This table shows file operation Version file."
    INDEX { wtpMacAddr }
    ::= { dot11WtpVersionFileUpdateTable 1 }
Dot11WtpVersionFileUpdateEntry ::=SEQUENCE{
	wtpVersionFileName		DisplayString,
	wtpMode			DisplayString,
	wtpFtpAddr			DisplayString,
	wtpUsrName			DisplayString,
	wtpPasswd			DisplayString,
	wtpUpdateAction			INTEGER
}
wtpVersionFileName			OBJECT-TYPE
					SYNTAX     DisplayString
					MAX-ACCESS read-write
					STATUS     current
					DESCRIPTION
				        	"Version file name."
					::= { dot11WtpVersionFileUpdateEntry 1 }

wtpMode				OBJECT-TYPE
					SYNTAX     DisplayString
					MAX-ACCESS read-write
					STATUS     current
					DESCRIPTION
				        	"Ap mode."
					::= { dot11WtpVersionFileUpdateEntry 2 }

wtpFtpAddr				OBJECT-TYPE
					SYNTAX     DisplayString
					MAX-ACCESS read-write
					STATUS     current
					DESCRIPTION
				        	"Ftp address."
					::= { dot11WtpVersionFileUpdateEntry 3 }

wtpUsrName				OBJECT-TYPE
					SYNTAX     DisplayString
					MAX-ACCESS read-write
					STATUS     current
					DESCRIPTION
				        	"User name."
					::= { dot11WtpVersionFileUpdateEntry 4 }

wtpPasswd				OBJECT-TYPE
					SYNTAX     DisplayString
					MAX-ACCESS read-write
					STATUS     current
					DESCRIPTION
				        	"password."
					::= { dot11WtpVersionFileUpdateEntry 5 }

wtpUpdateAction				OBJECT-TYPE
					SYNTAX     INTEGER{
							update(1)
							}
					MAX-ACCESS read-write
					STATUS     current
					DESCRIPTION
				        	"update action."
					::= { dot11WtpVersionFileUpdateEntry 6 }
					
--********************************************************************************************************
dot11WtpNetworkaddrTable OBJECT-TYPE
	    SYNTAX      SEQUENCE OF Dot11WtpNetworkaddrEntry
	    MAX-ACCESS  not-accessible
	    STATUS      current
	    DESCRIPTION
	        "This table shows AP network address information."
	    ::= { wtpGeneralInfo 5 }

dot11WtpNetworkaddrEntry  OBJECT-TYPE
    SYNTAX      Dot11WtpNetworkaddrEntry
    MAX-ACCESS  not-accessible
    STATUS      current
    DESCRIPTION
        "This table shows AP network address information."
    INDEX { wtpMacAddr }
    ::= { dot11WtpNetworkaddrTable 1 }
Dot11WtpNetworkaddrEntry ::=SEQUENCE{
	wtpIPAddress			IpAddress,
	wtpNetmask			IpAddress,
	wtpGateway			IpAddress,
	wtpFirstDNSServer		IpAddress,
	wtpSeconDNSServer		IpAddress,
	wtpSetAction			INTEGER
}
wtpIPAddress				OBJECT-TYPE
					SYNTAX     	IpAddress
					MAX-ACCESS 	read-write
					STATUS     	current
					DESCRIPTION
				        	"AP IP address."
					::= { dot11WtpNetworkaddrEntry 1 }

wtpNetmask				OBJECT-TYPE
					SYNTAX     	IpAddress
					MAX-ACCESS 	read-write
					STATUS     	current
					DESCRIPTION
				        	"AP address mask."
					::= { dot11WtpNetworkaddrEntry 2 }

wtpGateway				OBJECT-TYPE
					SYNTAX     	IpAddress
					MAX-ACCESS	 read-write
					STATUS     	current
					DESCRIPTION
				        	"The AP gateway address."
					::= { dot11WtpNetworkaddrEntry 3 }

					
wtpFirstDNSServer 			OBJECT-TYPE
					SYNTAX		IpAddress
					MAX-ACCESS 	read-write
					STATUS		current
					DESCRIPTION
						"The First DNS Server IP address.（AP）"
					::= { dot11WtpNetworkaddrEntry 4 }

wtpSeconDNSServer 			OBJECT-TYPE
					SYNTAX		IpAddress
					MAX-ACCESS 	read-write
					STATUS		current
					DESCRIPTION
						"The Second DNS Server IP address.（AP）"
					::= { dot11WtpNetworkaddrEntry 5 }

wtpSetAction				OBJECT-TYPE
					SYNTAX     	INTEGER{
								set(1)
								}
					MAX-ACCESS 	read-write
					STATUS     	current
					DESCRIPTION
				        	"set AP network address action."
					::= { dot11WtpNetworkaddrEntry 6 }	


dot11WtpRealTimeCollectTable OBJECT-TYPE
	    SYNTAX      SEQUENCE OF Dot11WtpRealTimeCollectEntry
	    MAX-ACCESS  not-accessible
	    STATUS      current
	    DESCRIPTION
	        "This table shows AP RealTime Pkt information."
	    ::= { wtpGeneralInfo 6 }
dot11WtpRealTimeCollectEntry  OBJECT-TYPE
    SYNTAX      Dot11WtpRealTimeCollectEntry
    MAX-ACCESS  not-accessible
    STATUS      current
    DESCRIPTION
        "This table shows AP RealTime Pkt information."
    INDEX { wtpMacAddr }
    ::= { dot11WtpRealTimeCollectTable 1 }	

Dot11WtpRealTimeCollectEntry ::=SEQUENCE{
        wtpRtCollectOnOff               INTEGER,
	CPURTUsage			INTEGER,
	MemRTUsage			INTEGER,
	wtpAssocTimes			Counter32,
	wtpAssocFailtimes		Counter32,
	wtpReassocTimes		        Counter32,
	wtpIfIndiscardPkts	        Counter32,
        wtpTxBytes                   	Counter64,
        wtpRxBytes                   	Counter64,
        wtpReassocFailure		Counter32,
        wtpSuccAssociatedNum		Counter32
}
wtpRtCollectOnOff 			OBJECT-TYPE
					SYNTAX     	INTEGER {
                                                                on(1),
                                                                off(2)   
                                                                }
					MAX-ACCESS 	read-write
					STATUS     	current
					DESCRIPTION
				        	"AP Information Switch."
					::= { dot11WtpRealTimeCollectEntry 1}

CPURTUsage				OBJECT-TYPE
					SYNTAX     	INTEGER
					MAX-ACCESS 	read-only
					STATUS     	current
					DESCRIPTION
				        	"AP Cpu RTUsage."
					::= { dot11WtpRealTimeCollectEntry 2  }

MemRTUsage				OBJECT-TYPE
					SYNTAX     	INTEGER
					MAX-ACCESS 	read-only
					STATUS     	current
					DESCRIPTION
				        	"AP MemRTUage."
					::= { dot11WtpRealTimeCollectEntry 3 }

wtpAssocTimes				OBJECT-TYPE
					SYNTAX     	Counter32
					MAX-ACCESS 	read-only
					STATUS     	current
					DESCRIPTION
				        	"AP Assoc Times ."
					::= { dot11WtpRealTimeCollectEntry 4  }

wtpAssocFailtimes				OBJECT-TYPE
					SYNTAX     	Counter32
					MAX-ACCESS 	read-only
					STATUS     	current
					DESCRIPTION
				        	"AP Assoc Fail times ."
					::= { dot11WtpRealTimeCollectEntry 5 }

wtpReassocTimes				OBJECT-TYPE
					SYNTAX     	Counter32
					MAX-ACCESS 	read-only
					STATUS     	current
					DESCRIPTION
				        	"AP Reassoc Times."
					::= { dot11WtpRealTimeCollectEntry 6 }

wtpIfIndiscardPkts			OBJECT-TYPE
					SYNTAX     	Counter32
					MAX-ACCESS 	read-only
					STATUS     	current
					DESCRIPTION
				        	"AP Receive Drop ."
					::= { dot11WtpRealTimeCollectEntry 7  }

wtpTxBytes			        OBJECT-TYPE
					SYNTAX     	Counter64
					MAX-ACCESS 	read-only
					STATUS     	current
					DESCRIPTION
				        	"AP Send Bytes."
					::= { dot11WtpRealTimeCollectEntry 8 }

wtpRxBytes			        OBJECT-TYPE
					SYNTAX     	Counter64
					MAX-ACCESS 	read-only
					STATUS     	current
					DESCRIPTION
				        	"AP Receive Bytes."
					::= { dot11WtpRealTimeCollectEntry 9 }
wtpReassocFailure		        OBJECT-TYPE
					SYNTAX     	Counter32
					MAX-ACCESS 	read-only
					STATUS     	current
					DESCRIPTION
				        	"AP Reassoc Failure times."
					::= { dot11WtpRealTimeCollectEntry 10 }
wtpSuccAssociatedNum		        OBJECT-TYPE
					SYNTAX     	Counter32
					MAX-ACCESS 	read-only
					STATUS     	current
					DESCRIPTION
				        	"AP Reassoc Failure times."
					::= { dot11WtpRealTimeCollectEntry 11 }

dot11NewWtpVersionFileUpdateTable OBJECT-TYPE
	    SYNTAX      SEQUENCE OF Dot11NewWtpVersionFileUpdateEntry
	    MAX-ACCESS  not-accessible
	    STATUS      current
	    DESCRIPTION
	        "This table shows file operation Version file."
	    ::= { wtpGeneralInfo 7 }

dot11NewWtpVersionFileUpdateEntry  OBJECT-TYPE
    SYNTAX      Dot11NewWtpVersionFileUpdateEntry
    MAX-ACCESS  not-accessible
    STATUS      current
    DESCRIPTION
        "This table shows file operation Version file."
    INDEX { wtpMacAddr }
    ::= { dot11NewWtpVersionFileUpdateTable 1 }
Dot11NewWtpVersionFileUpdateEntry ::=SEQUENCE{
	setWtpVersionFile		DisplayString

}
setWtpVersionFile			OBJECT-TYPE
					SYNTAX     DisplayString
					MAX-ACCESS read-write
					STATUS     current
					DESCRIPTION
				        	"FileName and Version."
					::= { dot11NewWtpVersionFileUpdateEntry 1 }








					
--********************************************************************************************************
dot11WtpWiredIfStatsTable OBJECT-TYPE
	    SYNTAX      SEQUENCE OF Dot11WtpWiredIfStatsEntry
	    MAX-ACCESS  not-accessible
	    STATUS      current
	    DESCRIPTION
	        "This table shows wired interface information."
	    ::= { wtpInterface 2 }

dot11WtpWiredIfStatsEntry  OBJECT-TYPE
    SYNTAX      Dot11WtpWiredIfStatsEntry
    MAX-ACCESS  not-accessible
    STATUS      current
    DESCRIPTION
        "Wired information."
    INDEX { wtpMacAddr,
		wtpIfIndex }
    ::= { dot11WtpWiredIfStatsTable 1 }
Dot11WtpWiredIfStatsEntry ::=SEQUENCE{
		wtpWiredifInUcastPkts		Counter32,
		wtpWiredifInNUcastPkts		Counter32,
		wtpWiredifInPkts		Counter32,
		wtpWiredifInDiscardPkts		Counter32,
		wtpWiredifInErrors		Counter32,
		wtpWiredifOutUcastPkts		Counter32,
		wtpWiredifOutNUcastPkts		Counter32,
		wtpWiredifOutPkts		Counter32,
		wtpWiredifOutDiscardPkts	Counter32,
		wtpWiredifOutErrors		Counter32,
		wtpWiredifUpDwnTimes		Counter32,
		wtpWiredifInOctets		Counter64,
		wtpWiredifOutOctets		Counter64,
		wtpWiredifInDataOctets		Counter64,
		wtpWiredifOutDataOctets		Counter64
}
wtpWiredifInUcastPkts			OBJECT-TYPE
					SYNTAX     Counter32 
					MAX-ACCESS read-only
					STATUS     current
					DESCRIPTION
				        	"Received the numbers of unicast packets."
					::= { dot11WtpWiredIfStatsEntry 1 }

wtpWiredifInNUcastPkts			OBJECT-TYPE
					SYNTAX     Counter32 
					MAX-ACCESS read-only
					STATUS     current
					DESCRIPTION
				        	"Received the numbers of non-unicast packets."
					::= { dot11WtpWiredIfStatsEntry 2 }

wtpWiredifInPkts			OBJECT-TYPE
					SYNTAX     Counter32 
					MAX-ACCESS read-only
					STATUS     current
					DESCRIPTION
				        	"The total number of received packets."
					::= { dot11WtpWiredIfStatsEntry 3 }

wtpWiredifInDiscardPkts			OBJECT-TYPE
					SYNTAX     Counter32 
					MAX-ACCESS read-only
					STATUS     current
					DESCRIPTION
				        	"Discarded packets received ."
					::= { dot11WtpWiredIfStatsEntry 4 }

wtpWiredifInErrors			OBJECT-TYPE
					SYNTAX     Counter32 
					MAX-ACCESS read-only
					STATUS     current
					DESCRIPTION
				        	"Error packets received."
					::= { dot11WtpWiredIfStatsEntry 5 }

wtpWiredifOutUcastPkts			OBJECT-TYPE
					SYNTAX     Counter32 
					MAX-ACCESS read-only
					STATUS     current
					DESCRIPTION
				        	"The number of unicast packets sended."
					::= { dot11WtpWiredIfStatsEntry 6 }

wtpWiredifOutNUcastPkts			OBJECT-TYPE
					SYNTAX     Counter32 
					MAX-ACCESS read-only
					STATUS     current
					DESCRIPTION
				        	"The number of sent non-unicast packets."
					::= { dot11WtpWiredIfStatsEntry 7 }

wtpWiredifOutPkts			OBJECT-TYPE
					SYNTAX     Counter32 
					MAX-ACCESS read-only
					STATUS     current
					DESCRIPTION
				        	"The total number of packets sent."
					::= { dot11WtpWiredIfStatsEntry 8 }

wtpWiredifOutDiscardPkts		OBJECT-TYPE
					SYNTAX     Counter32 
					MAX-ACCESS read-only
					STATUS     current
					DESCRIPTION
				        	"The number to send the packet which discarded."
					::= { dot11WtpWiredIfStatsEntry 9 }

wtpWiredifOutErrors			OBJECT-TYPE
					SYNTAX     Counter32 
					MAX-ACCESS read-only
					STATUS     current
					DESCRIPTION
				        	"The wrong number of packages which sent."
					::= { dot11WtpWiredIfStatsEntry 10 }

wtpWiredifUpDwnTimes			OBJECT-TYPE
					SYNTAX     Counter32 
					MAX-ACCESS read-only
					STATUS     current
					DESCRIPTION
				        	"Wired interface updown times."
					::= { dot11WtpWiredIfStatsEntry 11 }
					
wtpWiredifInOctets			OBJECT-TYPE
					SYNTAX     Counter64 
					MAX-ACCESS read-only
					STATUS     current
					DESCRIPTION
				        	"The total number of received bytes."
					::= { dot11WtpWiredIfStatsEntry 12 }	
					
wtpWiredifOutOctets			OBJECT-TYPE
					SYNTAX     Counter64 
					MAX-ACCESS read-only
					STATUS     current
					DESCRIPTION
				        	"The total number of bytes sent."
					::= { dot11WtpWiredIfStatsEntry 13 }	
wtpWiredifInDataOctets     		OBJECT-TYPE
					SYNTAX     Counter64 
					MAX-ACCESS read-only
					STATUS     current
					DESCRIPTION
				        	"The number of received data bytes."
					::= { dot11WtpWiredIfStatsEntry 14 }	
					
wtpWiredifOutDataOctets 		OBJECT-TYPE
					SYNTAX     Counter64 
					MAX-ACCESS read-only
					STATUS     current
					DESCRIPTION
				        	"The  number of send data bytes."
					::= { dot11WtpWiredIfStatsEntry 15 }	





							

dot11WtpWirelessIfTable OBJECT-TYPE
	    SYNTAX      SEQUENCE OF Dot11WtpWirelessIfEntry
	    MAX-ACCESS  not-accessible
	    STATUS      current
	    DESCRIPTION
	        "This table shows wireless interface information."
	    ::= { wtpInterface 3 }

dot11WtpWirelessIfEntry  OBJECT-TYPE
    SYNTAX      Dot11WtpWirelessIfEntry
    MAX-ACCESS  not-accessible
    STATUS      current
    DESCRIPTION
        "Wireless information."
    INDEX { wtpMacAddr,
		wtpWirelessIfIndex }
    ::= { dot11WtpWirelessIfTable 1 }
Dot11WtpWirelessIfEntry ::=SEQUENCE{
	wtpWirelessIfIndex				INTEGER,
	wtpWirelessIfDescr				DisplayString,
	wtpWirelessIfType				INTEGER,
	wtpWirelessIfMTU				INTEGER,
	wtpWirelessIfSpeed				Gauge32,
	wtpWirelessIfPhysAddress			PhysAddress,
	wtpWirelessIfAdminStatus			INTEGER,
	wtpWirelessIfOperStatus				INTEGER,
	wtpWirelessIfLastChange				TimeTicks,
	wtpWirelessIfRadioChannelAutoSelectEnable	INTEGER,
	wtpWirelessIfRadioChannelConfig			INTEGER,
	wtpWirelessIfDiversitySelectionRx		INTEGER,
	wtpWirelessIfCurrRadioModeSupport		INTEGER,
	wtpWirelessIfTransmitSpeedConfig		DisplayString,
	wtpWirelessIfPwrAttRange			INTEGER,
	wtpWirelessIfPwrAttValue			INTEGER,
	wtpWirelessIfAntennaGain			INTEGER,
	wtpWirelessIfPowerMgmtEnable			TruthValue,
	wtpWirelessIfMaxStationNumPermitted		INTEGER,
	wtpWirelessIfMaxTxPwrLvl			DisplayString,
	wtpWirelessIfTxPwrStep				INTEGER
}
wtpWirelessIfIndex				OBJECT-TYPE
						SYNTAX     INTEGER 
						MAX-ACCESS read-only
						STATUS     current
						DESCRIPTION
					        	"Wireless interface index."
						::= { dot11WtpWirelessIfEntry 1 }

wtpWirelessIfDescr				OBJECT-TYPE
						SYNTAX     DisplayString 
						MAX-ACCESS read-only
						STATUS     current
						DESCRIPTION
					        	"The information that describe wireless interface(microFX/wireless side SSID)."
						::= { dot11WtpWirelessIfEntry 2 }

wtpWirelessIfType				OBJECT-TYPE
						SYNTAX     INTEGER{
								Wifi(41)
								} 
						MAX-ACCESS read-only
						STATUS     current
						DESCRIPTION
					        	"Wireless interface type."
						::= { dot11WtpWirelessIfEntry 3 }

wtpWirelessIfMTU				OBJECT-TYPE
						SYNTAX     INTEGER 
						MAX-ACCESS read-only
						STATUS     current
						DESCRIPTION
					        	"Wireless interface MTU."
						::= { dot11WtpWirelessIfEntry 4 }

wtpWirelessIfSpeed				OBJECT-TYPE
						SYNTAX     Gauge32 
						MAX-ACCESS read-only
						STATUS     current
						DESCRIPTION
					        	"Wireless interface speed(UNIT Mbps)."
						::= { dot11WtpWirelessIfEntry 5 }

wtpWirelessIfPhysAddress			OBJECT-TYPE
						SYNTAX     PhysAddress 
						MAX-ACCESS read-only
						STATUS     current
						DESCRIPTION
					        	"Wireless interface MAC address."
						::= { dot11WtpWirelessIfEntry 6 }

wtpWirelessIfAdminStatus			OBJECT-TYPE
						SYNTAX     INTEGER{
								up(1),
								down(2)
								}
						MAX-ACCESS read-write
						STATUS     current
						DESCRIPTION
					        	"Wireless interface admin status."
						::= { dot11WtpWirelessIfEntry 7 }

wtpWirelessIfOperStatus				OBJECT-TYPE
						SYNTAX     INTEGER{
								up(1),
								down(2),
								testing(3),
								adminDown(4),
								dormant(5),
								notPresent(6),
								lowerLayerDown(7)
								}
						MAX-ACCESS read-only
						STATUS     current
						DESCRIPTION
					        	"Wireless interface current status."
						::= { dot11WtpWirelessIfEntry 8 }

wtpWirelessIfLastChange				OBJECT-TYPE
						SYNTAX     TimeTicks 
						MAX-ACCESS read-only
						STATUS     current
						DESCRIPTION
					        	"The last time the wireless interface into current work mode."
						::= { dot11WtpWirelessIfEntry 9 }

wtpWirelessIfRadioChannelAutoSelectEnable	OBJECT-TYPE
						SYNTAX     INTEGER{
								auto(1),
								manual(2)
								}
						MAX-ACCESS read-write
						STATUS     current
						DESCRIPTION
					        	"Whether select and config wireless channel ."
						::= { dot11WtpWirelessIfEntry 10 }

wtpWirelessIfRadioChannelConfig			OBJECT-TYPE
						SYNTAX     INTEGER(1..196)
						MAX-ACCESS read-write
						STATUS     current
						DESCRIPTION
					        	"If wireless channel select switch is closed,it needs to config wireless channel manually."
						::= { dot11WtpWirelessIfEntry 11 }

wtpWirelessIfDiversitySelectionRx		OBJECT-TYPE
						SYNTAX     INTEGER{
								true(1),
								false(0)
								}
						MAX-ACCESS read-only
						STATUS     current
						DESCRIPTION
					        	"If it is true,it means device supports receive diversit selection"
						::= { dot11WtpWirelessIfEntry 12 }

wtpWirelessIfCurrRadioModeSupport		OBJECT-TYPE
						SYNTAX     INTEGER{
							   a(1),
							   b(2),
							   g(4),
							   bg(6),
							   an(8),
							   aan(9),
							   gn(16),
							   ggn(20),
							   bggn(22)								
							   }
						MAX-ACCESS read-only
						STATUS     current
						DESCRIPTION
					        	"Supported wireless mode(All the above base on the 802.11 standard)."
						::= { dot11WtpWirelessIfEntry 13 }

wtpWirelessIfTransmitSpeedConfig		OBJECT-TYPE
						SYNTAX     DisplayString
						MAX-ACCESS read-write
						STATUS     current
						DESCRIPTION
					        	"Wireless interface transport speed.(The value you input must be 10,20,55,60,90,110,120,180,240,360,480,540,otherwise you will not set the value)"
						::= { dot11WtpWirelessIfEntry 14 }

wtpWirelessIfPwrAttRange			OBJECT-TYPE
						SYNTAX     INTEGER
						MAX-ACCESS read-only
						STATUS     current
						DESCRIPTION
					        	"Power attenuation range(units dB,not less than 20dB)."
						::= { dot11WtpWirelessIfEntry 15 }

wtpWirelessIfPwrAttValue			OBJECT-TYPE
						SYNTAX     INTEGER
						MAX-ACCESS read-write
						STATUS     current
						DESCRIPTION
					        	"Accuracy 0.5dB,step length 1dB."
						::= { dot11WtpWirelessIfEntry 16 }

wtpWirelessIfAntennaGain			OBJECT-TYPE
						SYNTAX     INTEGER
						MAX-ACCESS read-only
						STATUS     current
						DESCRIPTION
					        	"Antenna gain(units dBi)."
						::= { dot11WtpWirelessIfEntry 17 }

wtpWirelessIfPowerMgmtEnable			OBJECT-TYPE
						SYNTAX     INTEGER{
								ON(1),
								OFF(0)
								}
						MAX-ACCESS read-write
						STATUS     current
						DESCRIPTION
					        	"ON:AP configs transmission power automatically,power attenuation configuration invalid;OFF:manual adjustment,power attenuation configuration valid."
						::= { dot11WtpWirelessIfEntry 18 }

wtpWirelessIfMaxStationNumPermitted		OBJECT-TYPE
						SYNTAX     INTEGER(0..32767)
						MAX-ACCESS read-write
						STATUS     current
						DESCRIPTION
					        	"support max station number"
						::= { dot11WtpWirelessIfEntry 19 }
wtpWirelessIfMaxTxPwrLvl			OBJECT-TYPE
						SYNTAX     DisplayString
						MAX-ACCESS read-only
						STATUS     current
						DESCRIPTION
					        	"support max tx power"
						::= { dot11WtpWirelessIfEntry 20 }
						
wtpWirelessIfTxPwrStep				OBJECT-TYPE
						SYNTAX     INTEGER
						MAX-ACCESS read-write
						STATUS     current
						DESCRIPTION
					        	"txpower adjustment step"
						::= { dot11WtpWirelessIfEntry 21 }		


dot11WtpWirelessIfConfigTable OBJECT-TYPE
	    SYNTAX      SEQUENCE OF Dot11WtpWirelessIfConfigEntry
	    MAX-ACCESS  not-accessible
	    STATUS      current
	    DESCRIPTION
	        "This table shows wireless interface config."
	    ::= { wtpInterface 4 }

dot11WtpWirelessIfConfigEntry  OBJECT-TYPE
    SYNTAX      Dot11WtpWirelessIfConfigEntry
    MAX-ACCESS  not-accessible
    STATUS      current
    DESCRIPTION
        "Wireless config."
    INDEX { wtpMacAddr,
		wtpWirelessIfIndex }
    ::= { dot11WtpWirelessIfConfigTable 1 }

Dot11WtpWirelessIfConfigEntry ::=SEQUENCE{
	wtpWirelessIfBeaconIntvl			INTEGER,
	wtpWirelessIfDtimIntvl				INTEGER,
	wtpWirelessIfShtRetryThld			INTEGER,
	wtpWirelessIfLongRetryThld			INTEGER,
	wtpWirelessIfMaxRxLifetime			Unsigned32
}

wtpWirelessIfBeaconIntvl			OBJECT-TYPE
						SYNTAX     INTEGER(25..1000)
						UNITS		"ms"
						MAX-ACCESS read-write
						STATUS     current
						DESCRIPTION
					        	"Beacon frame interval.(Range25 - 1000ms)"
						::= { dot11WtpWirelessIfConfigEntry 1 }

wtpWirelessIfDtimIntvl				OBJECT-TYPE
						SYNTAX     INTEGER(1..15)
						MAX-ACCESS read-write
						STATUS     current
						DESCRIPTION
					        	"DTIM interval."
						::= { dot11WtpWirelessIfConfigEntry 2 }


wtpWirelessIfShtRetryThld			OBJECT-TYPE
						SYNTAX     INTEGER(1..15)
						MAX-ACCESS read-write
						STATUS     current
						DESCRIPTION
					        	"The total times that retry times when frame length less than RTS threshold  ."
						::= { dot11WtpWirelessIfConfigEntry 3 }

wtpWirelessIfLongRetryThld			OBJECT-TYPE
						SYNTAX     INTEGER(1..15)
						MAX-ACCESS read-write
						STATUS     current
						DESCRIPTION
					        	"The total times that retry times when frame length over RTS threshold  ."
						::= { dot11WtpWirelessIfConfigEntry 4 }

wtpWirelessIfMaxRxLifetime			OBJECT-TYPE
						SYNTAX     Unsigned32
						MAX-ACCESS read-write
						STATUS     current
						DESCRIPTION
					        	"Received data packets lifetime(units ms)."
						::= { dot11WtpWirelessIfConfigEntry 5 }
dot11WtpWirelessIfstatsTable OBJECT-TYPE
	    SYNTAX      SEQUENCE OF Dot11WtpWirelessIfstatsEntry
	    MAX-ACCESS  not-accessible
	    STATUS      current
	    DESCRIPTION
	        "This table shows wireless interface config."
	    ::= { wtpInterface 5 }

dot11WtpWirelessIfstatsEntry  OBJECT-TYPE
    SYNTAX      Dot11WtpWirelessIfstatsEntry
    MAX-ACCESS  not-accessible
    STATUS      current
    DESCRIPTION
        "Wireless config."
    INDEX { wtpMacAddr,
		wtpWirelessIfIndex }
    ::= { dot11WtpWirelessIfstatsTable 1 }

Dot11WtpWirelessIfstatsEntry ::=SEQUENCE{
		wirelessIfAvgRxSignalStrength		INTEGER,
		wirelessIfHighestRxSignalStrength	INTEGER,
		wirelessIfLowestRxSignalStrength	INTEGER,
		wirelessIfUpdownTimes			Counter32,
		wirelessIfChStatsNumStations		Counter32,
		wirelessIfTxSignalPkts			Counter32,
		wirelessIfRxSignalPkts			Counter32,
		wirelessIfTxDataPkts			Counter32,
		wirelessIfRxDataPkts			Counter32,
		wirelessIfRxDataOctets		        Counter64,
		wirelessIfTxDataOctets		        Counter64,
		wirelessIfChStatsDwlinkTotRetryPkts	Counter32,
		wirelessIfChStatsUplinkUniFrameCnt	Counter32,
		wirelessIfChStatsDwlinkUniFrameCnt	Counter32,
		wirelessIfUpChStatsFrameNonUniFrameCnt	Counter32,
		wirelessIfDownChStatsFrameNonUniFrameCnt	Counter32,
		wirelessIfChStatsPhyErrPkts		Counter32,
		wirelessIfChStatsMacFcsErrPkts		Counter32,
		wirelessIfChStatsMacMicErrPkts		Counter32,
		wirelessIfChStatsMacDecryptErrPkts	Counter32,
		wirelessIfChStatsFrameErrorCnt		Counter32,
		wirelessIfChStatsFrameRetryCnt		Counter32,
		wirelessIfApChStatsFrameFragRate	Counter32,
		wirelessIfRxMgmtFrameCnt		Counter32,
		wirelessIfRxCtrlFrameCnt		Counter32,
		wirelessIfRxDataFrameCnt		Counter32,
		wirelessIfRxAuthenFrameCnt		Counter32,
		wirelessIfRxAssociateFrameCnt		Counter32,
		wirelessIfTxMgmtFrameCnt		Counter32,
		wirelessIfTxCtrlFrameCnt		Counter32,
		wirelessIfTxDataFrameCnt		Counter32,
		wirelessIfTxAuthenFrameCnt		Counter32,
		wirelessIfTxAssociateFrameCnt		Counter32,
		wirelessIfTxManagePkts			Counter32,
		wirelessIfRxManagePkts			Counter32,
		wirelessIfTxManageOctets		Counter64,
		wirelessIfRxManageOctets		Counter64,
		wirelessIfTxTotalPkts			Counter32,
		wirelessIfRxTotalPkts			Counter32,
		wirelessIfTxTotalOctets		        Counter64,
		wirelessIfRxTotalOctets			Counter64,
		wirelessIfRxDropPkts			Counter32,
		wirelessIfTxDropPkts			Counter32,
		wirelessIfRxErrPkts			Counter32,
		wirelessIfTxErrPkts			Counter32,
		wtpNeighborSSIDList                     DisplayString
}
wirelessIfAvgRxSignalStrength			OBJECT-TYPE
						SYNTAX     INTEGER
						MAX-ACCESS read-only
						STATUS     current
						DESCRIPTION
					        	"The average received signal strength."
						::= { dot11WtpWirelessIfstatsEntry 1 }

wirelessIfHighestRxSignalStrength		OBJECT-TYPE
						SYNTAX     INTEGER
						MAX-ACCESS read-only
						STATUS     current
						DESCRIPTION
					        	"Receive the maximum signal strength."
						::= { dot11WtpWirelessIfstatsEntry 2 }

wirelessIfLowestRxSignalStrength		OBJECT-TYPE
						SYNTAX     INTEGER
						MAX-ACCESS read-only
						STATUS     current
						DESCRIPTION
					        	"Receive the minimum signal strength."
						::= { dot11WtpWirelessIfstatsEntry 3 }

wirelessIfUpdownTimes				OBJECT-TYPE
						SYNTAX     Counter32
						MAX-ACCESS read-only
						STATUS     current
						DESCRIPTION
					        	"Wireless interface updown times."
						::= { dot11WtpWirelessIfstatsEntry 4 }

wirelessIfChStatsNumStations			OBJECT-TYPE
						SYNTAX     Counter32
						MAX-ACCESS read-only
						STATUS     current
						DESCRIPTION
					        	"The terminals number which use the channel."
						::= { dot11WtpWirelessIfstatsEntry 5 }

wirelessIfTxSignalPkts				OBJECT-TYPE
						SYNTAX     Counter32
						MAX-ACCESS read-only
						STATUS     current
						DESCRIPTION
					        	 "The number of signaling packets which."
						::= { dot11WtpWirelessIfstatsEntry 6 }

wirelessIfRxSignalPkts				OBJECT-TYPE
						SYNTAX     Counter32
						MAX-ACCESS read-only
						STATUS     current
						DESCRIPTION
					        	"The number of signaling packets which received."
						::= { dot11WtpWirelessIfstatsEntry 7 }

wirelessIfTxDataPkts				OBJECT-TYPE
						SYNTAX     Counter32
						MAX-ACCESS read-only
						STATUS     current
						DESCRIPTION
					        	"The number of data packets which transmited."
						::= { dot11WtpWirelessIfstatsEntry 8 }

wirelessIfRxDataPkts				OBJECT-TYPE
						SYNTAX     Counter32
						MAX-ACCESS read-only
						STATUS     current
						DESCRIPTION
					        	"The number of data packets which received."
						::= { dot11WtpWirelessIfstatsEntry 9 }

wirelessIfRxDataOctets		        	OBJECT-TYPE
						SYNTAX     Counter64
						MAX-ACCESS read-only
						STATUS     current
						DESCRIPTION
					        	"The Number of data bytes received."
						::= { dot11WtpWirelessIfstatsEntry 10 }

wirelessIfTxDataOctets			        OBJECT-TYPE
						SYNTAX     Counter64
						MAX-ACCESS read-only
						STATUS     current
						DESCRIPTION
					        	"The Number of data bytes sent."
						::= { dot11WtpWirelessIfstatsEntry 11 }

wirelessIfChStatsDwlinkTotRetryPkts		OBJECT-TYPE
						SYNTAX     Counter32
						MAX-ACCESS read-only
						STATUS     current
						DESCRIPTION
					        	"Retransmission packets number."
						::= { dot11WtpWirelessIfstatsEntry 12 }

wirelessIfChStatsUplinkUniFrameCnt		OBJECT-TYPE
						SYNTAX     Counter32
						MAX-ACCESS read-only
						STATUS     current
						DESCRIPTION
					        	"The total number of uplink uniframes on wireless channel."
						::= { dot11WtpWirelessIfstatsEntry 13 }

wirelessIfChStatsDwlinkUniFrameCnt		OBJECT-TYPE
						SYNTAX     Counter32
						MAX-ACCESS read-only
						STATUS     current
						DESCRIPTION
					        	"The total number of downlink uniframes on wireless channel."
						::= { dot11WtpWirelessIfstatsEntry 14 }

wirelessIfUpChStatsFrameNonUniFrameCnt		OBJECT-TYPE
						SYNTAX     Counter32
						MAX-ACCESS read-only
						STATUS     current
						DESCRIPTION
					        	"The total number of uplink nonuniframes on wireless channel."
						::= { dot11WtpWirelessIfstatsEntry 15 }

wirelessIfDownChStatsFrameNonUniFrameCnt		OBJECT-TYPE
						SYNTAX     Counter32
						MAX-ACCESS read-only
						STATUS     current
						DESCRIPTION
					        	"The total number of downlink nonuniframes on wireless channel."
						::= { dot11WtpWirelessIfstatsEntry 16 }

wirelessIfChStatsPhyErrPkts			OBJECT-TYPE
						SYNTAX     Counter32
						MAX-ACCESS read-only
						STATUS     current
						DESCRIPTION
					        	"The total number of physical error packets on wireless channel."
						::= { dot11WtpWirelessIfstatsEntry 17 }

wirelessIfChStatsMacFcsErrPkts			OBJECT-TYPE
						SYNTAX     Counter32
						MAX-ACCESS read-only
						STATUS     current
						DESCRIPTION
					        	"The total number of Fcs mac error packets on wireless channel."
						::= { dot11WtpWirelessIfstatsEntry 18 }

wirelessIfChStatsMacMicErrPkts			OBJECT-TYPE
						SYNTAX     Counter32
						MAX-ACCESS read-only
						STATUS     current
						DESCRIPTION
					        	"The total number of Mic mac error packets on wireless channel."
						::= { dot11WtpWirelessIfstatsEntry 19 }

wirelessIfChStatsMacDecryptErrPkts		OBJECT-TYPE
						SYNTAX     Counter32
						MAX-ACCESS read-only
						STATUS     current
						DESCRIPTION
					        	"The total number of decryption failed mac error packets on wireless channel."
						::= { dot11WtpWirelessIfstatsEntry 20 }

wirelessIfChStatsFrameErrorCnt			OBJECT-TYPE
						SYNTAX     Counter32
						MAX-ACCESS read-only
						STATUS     current
						DESCRIPTION
					        	"The total number of error frames which the channel received."
						::= { dot11WtpWirelessIfstatsEntry 21 }

wirelessIfChStatsFrameRetryCnt			OBJECT-TYPE
						SYNTAX     Counter32
						MAX-ACCESS read-only
						STATUS     current
						DESCRIPTION
					        	"The total number of retry frames on the channel."
						::= { dot11WtpWirelessIfstatsEntry 22 }

wirelessIfApChStatsFrameFragRate		OBJECT-TYPE
						SYNTAX     Counter32
						MAX-ACCESS read-only
						STATUS     current
						DESCRIPTION
					        	"Channel sub-frame rate."
						::= { dot11WtpWirelessIfstatsEntry 23 }	

wirelessIfRxMgmtFrameCnt			OBJECT-TYPE
						SYNTAX     Counter32
						MAX-ACCESS read-only
						STATUS     current
						DESCRIPTION
					        	"Received the number of management frames."
						::= { dot11WtpWirelessIfstatsEntry 24 }

wirelessIfRxCtrlFrameCnt			OBJECT-TYPE
						SYNTAX     Counter32
						MAX-ACCESS read-only
						STATUS     current
						DESCRIPTION
					        	"Received the number of control frames."
						::= { dot11WtpWirelessIfstatsEntry 25 }

wirelessIfRxDataFrameCnt			OBJECT-TYPE
						SYNTAX     Counter32
						MAX-ACCESS read-only
						STATUS     current
						DESCRIPTION
					        	"Received the number of data frames."
						::= { dot11WtpWirelessIfstatsEntry 26 }

wirelessIfRxAuthenFrameCnt			OBJECT-TYPE
						SYNTAX     Counter32
						MAX-ACCESS read-only
						STATUS     current
						DESCRIPTION
					        	"Received the number of certification frames."
						::= { dot11WtpWirelessIfstatsEntry 27 }

wirelessIfRxAssociateFrameCnt			OBJECT-TYPE
						SYNTAX     Counter32
						MAX-ACCESS read-only
						STATUS     current
						DESCRIPTION
					        	"Received the number of associated frames."
						::= { dot11WtpWirelessIfstatsEntry 28 }

wirelessIfTxMgmtFrameCnt			OBJECT-TYPE
						SYNTAX     Counter32
						MAX-ACCESS read-only
						STATUS     current
						DESCRIPTION
					        	"Send the number of management frames."
						::= { dot11WtpWirelessIfstatsEntry 29 }

wirelessIfTxCtrlFrameCnt			OBJECT-TYPE
						SYNTAX     Counter32
						MAX-ACCESS read-only
						STATUS     current
						DESCRIPTION
					        	"Send the number of control frames."
						::= { dot11WtpWirelessIfstatsEntry 30 }

wirelessIfTxDataFrameCnt			OBJECT-TYPE
						SYNTAX     Counter32
						MAX-ACCESS read-only
						STATUS     current
						DESCRIPTION
					        	"Sent the number of data frames."
						::= { dot11WtpWirelessIfstatsEntry 31 }

wirelessIfTxAuthenFrameCnt			OBJECT-TYPE
						SYNTAX     Counter32
						MAX-ACCESS read-only
						STATUS     current
						DESCRIPTION
					        	"Send the number of certification frames."
						::= { dot11WtpWirelessIfstatsEntry 32 }

wirelessIfTxAssociateFrameCnt			OBJECT-TYPE
						SYNTAX     Counter32
						MAX-ACCESS read-only
						STATUS     current
						DESCRIPTION
					        	"Send the link of the number of frames."
						::= { dot11WtpWirelessIfstatsEntry 33 }
wirelessIfTxManagePkts				OBJECT-TYPE
						SYNTAX     Counter32
						MAX-ACCESS read-only
						STATUS     current
						DESCRIPTION
					        	"The number of send management pkts."
						::= { dot11WtpWirelessIfstatsEntry 34 }	
wirelessIfRxManagePkts				OBJECT-TYPE
						SYNTAX     Counter32
						MAX-ACCESS read-only
						STATUS     current
						DESCRIPTION
					        	"The number of received management pkts."
						::= { dot11WtpWirelessIfstatsEntry 35 }	
wirelessIfTxManageOctets			OBJECT-TYPE
						SYNTAX     Counter64
						MAX-ACCESS read-only
						STATUS     current
						DESCRIPTION
					        	"The number of send management bytes."
						::= { dot11WtpWirelessIfstatsEntry 36 }	
wirelessIfRxManageOctets			OBJECT-TYPE
						SYNTAX     Counter64
						MAX-ACCESS read-only
						STATUS     current
						DESCRIPTION
					        	"The number of received management bytes."
						::= { dot11WtpWirelessIfstatsEntry 37 }	
wirelessIfTxTotalPkts				OBJECT-TYPE
						SYNTAX     Counter32
						MAX-ACCESS read-only
						STATUS     current
						DESCRIPTION
					        	"."
						::= { dot11WtpWirelessIfstatsEntry 38 }	
wirelessIfRxTotalPkts				OBJECT-TYPE
						SYNTAX     Counter32
						MAX-ACCESS read-only
						STATUS     current
						DESCRIPTION
					        	"."
						::= { dot11WtpWirelessIfstatsEntry 39 }	
wirelessIfTxTotalOctets			        OBJECT-TYPE
						SYNTAX     Counter64
						MAX-ACCESS read-only
						STATUS     current
						DESCRIPTION
					        	"The total number of radio send packet bytes."
						::= { dot11WtpWirelessIfstatsEntry 40 }	
wirelessIfRxTotalOctets			        OBJECT-TYPE
						SYNTAX     Counter64
						MAX-ACCESS read-only
						STATUS     current
						DESCRIPTION
					        	"The total number of radio received packet bytes."
						::= { dot11WtpWirelessIfstatsEntry 41 }						
						
wirelessIfRxDropPkts			        OBJECT-TYPE
						SYNTAX     Counter32
						MAX-ACCESS read-only
						STATUS     current
						DESCRIPTION
					        	"The total number of radio received drop packets."
						::= { dot11WtpWirelessIfstatsEntry 42 }	

wirelessIfTxDropPkts			        OBJECT-TYPE
						SYNTAX     Counter32
						MAX-ACCESS read-only
						STATUS     current
						DESCRIPTION
					        	"The total number of radio send drop packets."
						::= { dot11WtpWirelessIfstatsEntry 43 }			

wirelessIfRxErrPkts			        OBJECT-TYPE
						SYNTAX     Counter32
						MAX-ACCESS read-only
						STATUS     current
						DESCRIPTION
					        	"The total number of radio received error packets."
						::= { dot11WtpWirelessIfstatsEntry 44 }			
			
wirelessIfTxErrPkts			        OBJECT-TYPE
						SYNTAX     Counter32
						MAX-ACCESS read-only
						STATUS     current
						DESCRIPTION
					        	"The total number of radio send error packets."
						::= { dot11WtpWirelessIfstatsEntry 45 }		

wtpNeighborSSIDList		        	OBJECT-TYPE
						SYNTAX     DisplayString 
						MAX-ACCESS read-only
						STATUS     current
						DESCRIPTION
				        		"The wtp Neighbor SSID List."
						::= { dot11WtpWirelessIfstatsEntry 46 }				
--*********************************************************************************************
dot11WtpWiredIfMulticastTable OBJECT-TYPE
	    SYNTAX      SEQUENCE OF Dot11WtpWiredIfMulticastEntry
	    MAX-ACCESS  not-accessible
	    STATUS      current
	    DESCRIPTION
	        "Multicast pkts."
	    ::= { wtpInterface 6 }

dot11WtpWiredIfMulticastEntry  OBJECT-TYPE
    SYNTAX      Dot11WtpWiredIfMulticastEntry
    MAX-ACCESS  not-accessible
    STATUS      current
    DESCRIPTION
        "Multicast pkts."
    INDEX { wtpMacAddr,
		wtpIfIndex }
    ::= { dot11WtpWiredIfMulticastTable 1 }

Dot11WtpWiredIfMulticastEntry ::=SEQUENCE{
		wtpWiredIfInMulticastPkts	Counter32,
		wtpWiredIfOutMulticastPkts	Counter32
}

wtpWiredIfInMulticastPkts		OBJECT-TYPE
					SYNTAX     Counter32 
					MAX-ACCESS read-only
					STATUS     current
					DESCRIPTION
				        	"The total number of multicast  packages which received."
					::= { dot11WtpWiredIfMulticastEntry 1 }

wtpWiredIfOutMulticastPkts		OBJECT-TYPE
					SYNTAX     Counter32 
					MAX-ACCESS read-only
					STATUS     current
					DESCRIPTION
				        	"The total number of multicast  packages which sent."
					::= { dot11WtpWiredIfMulticastEntry 2 }



dot11WtpWirelessCapStatTable OBJECT-TYPE
	    SYNTAX      SEQUENCE OF Dot11WtpWirelessCapStatEntry
	    MAX-ACCESS  not-accessible
	    STATUS      current
	    DESCRIPTION
	        "Wireless Capablity statistics ."
	    ::= { wtpInterface 7}

dot11WtpWirelessCapStatEntry  OBJECT-TYPE
    SYNTAX      Dot11WtpWirelessCapStatEntry
    MAX-ACCESS  not-accessible
    STATUS      current
    DESCRIPTION
        "Wireless Capablity statistics."
    INDEX { wtpMacAddr,
		wtpWirelessIfIndex }
    ::= { dot11WtpWirelessCapStatTable 1 }

Dot11WtpWirelessCapStatEntry ::=SEQUENCE{
		AvgRxSignalStrength     DisplayString,
	        HighestRxSignalStrength	DisplayString,
                LowestRxSignalStrength  DisplayString,
                ChstatsPhyerrPkts       Counter32,
                ChstatsFrameRetryCnt    Counter32,
                ChstatsFrameErrorCnt    Counter32
                }

AvgRxSignalStrength		        OBJECT-TYPE
					SYNTAX     DisplayString 
					MAX-ACCESS read-only
					STATUS     current
					DESCRIPTION
				        	"The Average Signal Strength which have recieved."
					::= { dot11WtpWirelessCapStatEntry 1 }

HighestRxSignalStrength		        OBJECT-TYPE
					SYNTAX     DisplayString 
					MAX-ACCESS read-only
					STATUS     current
					DESCRIPTION
				        	"The Hightest Signal Strength which have recieved."
					::= { dot11WtpWirelessCapStatEntry 2 }

LowestRxSignalStrength		        OBJECT-TYPE
					SYNTAX     DisplayString 
					MAX-ACCESS read-only
					STATUS     current
					DESCRIPTION
				        	"The Lowerst Signal Strength which have recieved."
					::= { dot11WtpWirelessCapStatEntry 3}

ChstatsPhyerrPkts 		        OBJECT-TYPE
					SYNTAX     Counter32 
					MAX-ACCESS read-only
					STATUS     current
					DESCRIPTION
				        	"The Phy error Pkts which have recieved."
					::= { dot11WtpWirelessCapStatEntry 4 }

ChstatsFrameRetryCnt		        OBJECT-TYPE
					SYNTAX     Counter32 
					MAX-ACCESS read-only
					STATUS     current
					DESCRIPTION
				        	"The Frame Retry which have recieved."
					::= { dot11WtpWirelessCapStatEntry 5}

ChstatsFrameErrorCnt		        OBJECT-TYPE
					SYNTAX     Counter32 
					MAX-ACCESS read-only
					STATUS     current
					DESCRIPTION
				        	"The Frame Error which have recieved."
					::= { dot11WtpWirelessCapStatEntry 6}
dot11NewWtpWirelessIfstatsTable OBJECT-TYPE
	    SYNTAX      SEQUENCE OF Dot11NewWtpWirelessIfstatsEntry
	    MAX-ACCESS  not-accessible
	    STATUS      current
	    DESCRIPTION
	        "This table shows wireless interface config."
	    ::= { wtpInterface 8 }

dot11NewWtpWirelessIfstatsEntry  OBJECT-TYPE
    SYNTAX      Dot11NewWtpWirelessIfstatsEntry
    MAX-ACCESS  not-accessible
    STATUS      current
    DESCRIPTION
        "Wireless config."
    INDEX { wtpMacAddr,
		wtpWirelessIfIndex ,
                NewWirelessWlanID }
    ::= { dot11NewWtpWirelessIfstatsTable 1 }

Dot11NewWtpWirelessIfstatsEntry ::=SEQUENCE{  
                NewWirelessWlanID                                  INTEGER,
		NewwirelessIfAvgRxSignalStrength		INTEGER,
		NewwirelessIfHighestRxSignalStrength	INTEGER,
		NewwirelessIfLowestRxSignalStrength	INTEGER,
		NewwirelessIfUpdownTimes			Counter32,
		NewwirelessIfChStatsNumStations		INTEGER,
		NewwirelessIfTxSignalPkts			Counter32,
		NewwirelessIfRxSignalPkts			Counter32,
		NewwirelessIfTxDataPkts			Counter32,
		NewwirelessIfRxDataPkts			Counter32,
		NewwirelessIfTxbytes		        Counter64,
		NewwirelessIfRxbytes		        Counter64,
		NewwirelessIfChStatsDwlinkTotRetryPkts	Counter32,
		NewwirelessIfChStatsUplinkUniFrameCnt	Counter64,
		NewwirelessIfChStatsDwlinkUniFrameCnt	Counter64,
		NewwirelessIfUpChStatsFrameNonUniFrameCnt	Counter32,
		NewwirelessIfDownChStatsFrameNonUniFrameCnt	Counter32,
		NewwirelessIfChStatsPhyErrPkts		Counter32,
		NewwirelessIfChStatsMacFcsErrPkts		Counter32,
		NewwirelessIfChStatsMacMicErrPkts		Counter32,
		NewwirelessIfChStatsMacDecryptErrPkts	Counter32,
		NewwirelessIfChStatsFrameErrorCnt		Counter32,
		NewwirelessIfChStatsFrameRetryCnt		Counter32,
		NewwirelessIfApChStatsFrameFragRate	Counter32,
		NewwirelessIfRxMgmtFrameCnt		Counter32,
		NewwirelessIfRxCtrlFrameCnt		Counter32,
		NewwirelessIfRxDataFrameCnt		Counter32,
		NewwirelessIfRxAuthenFrameCnt		Counter32,
		NewwirelessIfRxAssociateFrameCnt		Counter32,
		NewwirelessIfTxMgmtFrameCnt		Counter32,
		NewwirelessIfTxCtrlFrameCnt		Counter32,
		NewwirelessIfTxDataFrameCnt		Counter32,
		NewwirelessIfTxAuthenFrameCnt		Counter32,
		NewwirelessIfTxAssociateFrameCnt		Counter32,
		NewwirelessIfSuccAssociatedNum		Counter32,
		NewwirelessIfallApUserOnlineTime                    TimeTicks,
		NewwirelessIfApUserLostConnectionCnt                 Counter32,
		NewwirelessIfApAuthReqCnt                            Counter32,
		NewwirelessIfApAuthSucCnt                            Counter32,
		NewwirelessIfApAuthFailCnt                           Counter32
}


NewWirelessWlanID			        OBJECT-TYPE
						SYNTAX     INTEGER
						MAX-ACCESS read-only
						STATUS     current
						DESCRIPTION
					        	"WlanID."
						::= { dot11NewWtpWirelessIfstatsEntry 1 }

NewwirelessIfAvgRxSignalStrength			OBJECT-TYPE
						SYNTAX     INTEGER
						MAX-ACCESS read-only
						STATUS     current
						DESCRIPTION
					        	"The average received signal strength."
						::= { dot11NewWtpWirelessIfstatsEntry 2}

NewwirelessIfHighestRxSignalStrength		OBJECT-TYPE
						SYNTAX     INTEGER
						MAX-ACCESS read-only
						STATUS     current
						DESCRIPTION
					        	"Receive the maximum signal strength."
						::= { dot11NewWtpWirelessIfstatsEntry 3 }

NewwirelessIfLowestRxSignalStrength		OBJECT-TYPE
						SYNTAX     INTEGER
						MAX-ACCESS read-only
						STATUS     current
						DESCRIPTION
					        	"Receive the minimum signal strength."
						::= { dot11NewWtpWirelessIfstatsEntry 4 }

NewwirelessIfUpdownTimes				OBJECT-TYPE
						SYNTAX     Counter32
						MAX-ACCESS read-only
						STATUS     current
						DESCRIPTION
					        	"Wireless interface updown times."
						::= { dot11NewWtpWirelessIfstatsEntry 5 }

NewwirelessIfChStatsNumStations			OBJECT-TYPE
						SYNTAX     INTEGER
						MAX-ACCESS read-only
						STATUS     current
						DESCRIPTION
					        	"The terminals number which use the channel."
						::= { dot11NewWtpWirelessIfstatsEntry 6 }

NewwirelessIfTxSignalPkts				OBJECT-TYPE
						SYNTAX     Counter32
						MAX-ACCESS read-only
						STATUS     current
						DESCRIPTION
					        	 "The number of signaling packets which."
						::= { dot11NewWtpWirelessIfstatsEntry 7 }

NewwirelessIfRxSignalPkts				OBJECT-TYPE
						SYNTAX     Counter32
						MAX-ACCESS read-only
						STATUS     current
						DESCRIPTION
					        	"The number of signaling packets which received."
						::= { dot11NewWtpWirelessIfstatsEntry 8 }

NewwirelessIfTxDataPkts				OBJECT-TYPE
						SYNTAX     Counter32
						MAX-ACCESS read-only
						STATUS     current
						DESCRIPTION
					        	"The number of data packets which transmited."
						::= { dot11NewWtpWirelessIfstatsEntry 9 }

NewwirelessIfRxDataPkts				OBJECT-TYPE
						SYNTAX     Counter32
						MAX-ACCESS read-only
						STATUS     current
						DESCRIPTION
					        	"The number of data packets which received."
						::= { dot11NewWtpWirelessIfstatsEntry 10 }

NewwirelessIfTxbytes			        OBJECT-TYPE
						SYNTAX     Counter64
						MAX-ACCESS read-only
						STATUS     current
						DESCRIPTION
					        	"Number of bytes sent."
						::= { dot11NewWtpWirelessIfstatsEntry 11 }

NewwirelessIfRxbytes			        OBJECT-TYPE
						SYNTAX     Counter64
						MAX-ACCESS read-only
						STATUS     current
						DESCRIPTION
					        	"Number of bytes received."
						::= { dot11NewWtpWirelessIfstatsEntry 12}

NewwirelessIfChStatsDwlinkTotRetryPkts		OBJECT-TYPE
						SYNTAX     Counter32
						MAX-ACCESS read-only
						STATUS     current
						DESCRIPTION
					        	"Retransmission packets number."
						::= { dot11NewWtpWirelessIfstatsEntry 13 }

NewwirelessIfChStatsUplinkUniFrameCnt		OBJECT-TYPE
						SYNTAX     Counter64
						MAX-ACCESS read-only
						STATUS     current
						DESCRIPTION
					        	"."
						::= { dot11NewWtpWirelessIfstatsEntry 14 }

NewwirelessIfChStatsDwlinkUniFrameCnt		OBJECT-TYPE
						SYNTAX     Counter64
						MAX-ACCESS read-only
						STATUS     current
						DESCRIPTION
					        	"."
						::= { dot11NewWtpWirelessIfstatsEntry 15 }

NewwirelessIfUpChStatsFrameNonUniFrameCnt		OBJECT-TYPE
						SYNTAX     Counter32
						MAX-ACCESS read-only
						STATUS     current
						DESCRIPTION
					        	"."
						::= { dot11NewWtpWirelessIfstatsEntry 16 }

NewwirelessIfDownChStatsFrameNonUniFrameCnt		OBJECT-TYPE
						SYNTAX     Counter32
						MAX-ACCESS read-only
						STATUS     current
						DESCRIPTION
					        	"."
						::= { dot11NewWtpWirelessIfstatsEntry 17 }

NewwirelessIfChStatsPhyErrPkts			OBJECT-TYPE
						SYNTAX     Counter32
						MAX-ACCESS read-only
						STATUS     current
						DESCRIPTION
					        	"."
						::= { dot11NewWtpWirelessIfstatsEntry 18 }

NewwirelessIfChStatsMacFcsErrPkts			OBJECT-TYPE
						SYNTAX     Counter32
						MAX-ACCESS read-only
						STATUS     current
						DESCRIPTION
					        	"."
						::= { dot11NewWtpWirelessIfstatsEntry 19 }

NewwirelessIfChStatsMacMicErrPkts			OBJECT-TYPE
						SYNTAX     Counter32
						MAX-ACCESS read-only
						STATUS     current
						DESCRIPTION
					        	"."
						::= { dot11NewWtpWirelessIfstatsEntry 20 }

NewwirelessIfChStatsMacDecryptErrPkts		OBJECT-TYPE
						SYNTAX     Counter32
						MAX-ACCESS read-only
						STATUS     current
						DESCRIPTION
					        	"."
						::= { dot11NewWtpWirelessIfstatsEntry 21 }

NewwirelessIfChStatsFrameErrorCnt			OBJECT-TYPE
						SYNTAX     Counter32
						MAX-ACCESS read-only
						STATUS     current
						DESCRIPTION
					        	"."
						::= { dot11NewWtpWirelessIfstatsEntry 22 }

NewwirelessIfChStatsFrameRetryCnt			OBJECT-TYPE
						SYNTAX     Counter32
						MAX-ACCESS read-only
						STATUS     current
						DESCRIPTION
					        	"."
						::= { dot11NewWtpWirelessIfstatsEntry 23 }

NewwirelessIfApChStatsFrameFragRate		OBJECT-TYPE
						SYNTAX     Counter32
						MAX-ACCESS read-only
						STATUS     current
						DESCRIPTION
					        	"."
						::= { dot11NewWtpWirelessIfstatsEntry 24 }	

NewwirelessIfRxMgmtFrameCnt			OBJECT-TYPE
						SYNTAX     Counter32
						MAX-ACCESS read-only
						STATUS     current
						DESCRIPTION
					        	"."
						::= { dot11NewWtpWirelessIfstatsEntry 25 }

NewwirelessIfRxCtrlFrameCnt			OBJECT-TYPE
						SYNTAX     Counter32
						MAX-ACCESS read-only
						STATUS     current
						DESCRIPTION
					        	"."
						::= { dot11NewWtpWirelessIfstatsEntry 26 }

NewwirelessIfRxDataFrameCnt			OBJECT-TYPE
						SYNTAX     Counter32
						MAX-ACCESS read-only
						STATUS     current
						DESCRIPTION
					        	"."
						::= { dot11NewWtpWirelessIfstatsEntry 27}

NewwirelessIfRxAuthenFrameCnt			OBJECT-TYPE
						SYNTAX     Counter32
						MAX-ACCESS read-only
						STATUS     current
						DESCRIPTION
					        	"."
						::= { dot11NewWtpWirelessIfstatsEntry 28 }

NewwirelessIfRxAssociateFrameCnt			OBJECT-TYPE
						SYNTAX     Counter32
						MAX-ACCESS read-only
						STATUS     current
						DESCRIPTION
					        	"."
						::= { dot11NewWtpWirelessIfstatsEntry 29 }

NewwirelessIfTxMgmtFrameCnt			OBJECT-TYPE
						SYNTAX     Counter32
						MAX-ACCESS read-only
						STATUS     current
						DESCRIPTION
					        	"."
						::= { dot11NewWtpWirelessIfstatsEntry 30 }

NewwirelessIfTxCtrlFrameCnt			OBJECT-TYPE
						SYNTAX     Counter32
						MAX-ACCESS read-only
						STATUS     current
						DESCRIPTION
					        	"."
						::= { dot11NewWtpWirelessIfstatsEntry 31 }

NewwirelessIfTxDataFrameCnt			OBJECT-TYPE
						SYNTAX     Counter32
						MAX-ACCESS read-only
						STATUS     current
						DESCRIPTION
					        	"."
						::= { dot11NewWtpWirelessIfstatsEntry 32 }

NewwirelessIfTxAuthenFrameCnt			OBJECT-TYPE
						SYNTAX     Counter32
						MAX-ACCESS read-only
						STATUS     current
						DESCRIPTION
					        	"."
						::= { dot11NewWtpWirelessIfstatsEntry 33 }

NewwirelessIfTxAssociateFrameCnt			OBJECT-TYPE
						SYNTAX     Counter32
						MAX-ACCESS read-only
						STATUS     current
						DESCRIPTION
					        	"."
						::= { dot11NewWtpWirelessIfstatsEntry 34 }
						
NewwirelessIfSuccAssociatedNum			OBJECT-TYPE
						SYNTAX     Counter32
						MAX-ACCESS read-only
						STATUS     current
						DESCRIPTION
					        	"."
						::= { dot11NewWtpWirelessIfstatsEntry 35 }					
NewwirelessIfallApUserOnlineTime			OBJECT-TYPE
						SYNTAX     TimeTicks
						MAX-ACCESS read-only
						STATUS     current
						DESCRIPTION
					        	" The all users online time of AP."
						::= { dot11NewWtpWirelessIfstatsEntry 42 }
NewwirelessIfApUserLostConnectionCnt				OBJECT-TYPE
						SYNTAX     Counter32
						MAX-ACCESS read-only
						STATUS     current
						DESCRIPTION
					        	" The total fail number of AP."
						::= { dot11NewWtpWirelessIfstatsEntry 43 }
NewwirelessIfApAuthReqCnt				OBJECT-TYPE
						SYNTAX     Counter32
						MAX-ACCESS read-only
						STATUS     current
						DESCRIPTION
					        	" The total request number of AP."
						::= { dot11NewWtpWirelessIfstatsEntry 44 }
NewwirelessIfApAuthSucCnt				OBJECT-TYPE
						SYNTAX     Counter32
						MAX-ACCESS read-only
						STATUS     current
						DESCRIPTION
					        	" The total request success number of AP."
						::= { dot11NewWtpWirelessIfstatsEntry 45 }
NewwirelessIfApAuthFailCnt			OBJECT-TYPE
						SYNTAX     Counter32
						MAX-ACCESS read-only
						STATUS     current
						DESCRIPTION
					        	" The total request fail number of AP."
						::= { dot11NewWtpWirelessIfstatsEntry 46 }
--********************************************************************************************************						
dot11NewWtpWirelessIfConfigTable OBJECT-TYPE
	    SYNTAX      SEQUENCE OF Dot11NewWtpWirelessIfConfigEntry
	    MAX-ACCESS  not-accessible
	    STATUS      current
	    DESCRIPTION
	        "This table shows wireless interface config."
	    ::= { wtpInterface 9 }

dot11NewWtpWirelessIfConfigEntry  OBJECT-TYPE
    SYNTAX      Dot11NewWtpWirelessIfConfigEntry
    MAX-ACCESS  not-accessible
    STATUS      current
    DESCRIPTION
        "Wireless config."
    INDEX { NewwtpID,
		NewapWirelessIfIndex }
    ::= { dot11NewWtpWirelessIfConfigTable 1 }

Dot11NewWtpWirelessIfConfigEntry ::=SEQUENCE{  
        NewwtpID                                        INTEGER,
        NewapWirelessIfIndex                           INTEGER,
	NewwtpWirelessIfBeaconIntvl			INTEGER,
	NewwtpWirelessIfDtimIntvl		        INTEGER,
	NewwtpWirelessIfShtRetryThld			INTEGER,
	NewwtpWirelessIfLongRetryThld			INTEGER,
	NewwtpWirelessIfMaxRxLifetime			Unsigned32,
        NewWtpPreambleLen                               INTEGER,
        NewRtsThreshold                                 Integer32,
        NewFragThreshlod                                Integer32
}
NewwtpID			                OBJECT-TYPE
						SYNTAX     INTEGER					
						MAX-ACCESS read-only
						STATUS     current
						DESCRIPTION
					        	"wtpID"
						::= { dot11NewWtpWirelessIfConfigEntry 1 }

NewapWirelessIfIndex			        OBJECT-TYPE
						SYNTAX     INTEGER
						MAX-ACCESS read-only
						STATUS     current
						DESCRIPTION
					        	"wtpWirelessIfIndex	"
						::= { dot11NewWtpWirelessIfConfigEntry 2 }

NewwtpWirelessIfBeaconIntvl			OBJECT-TYPE
						SYNTAX     INTEGER(25..1000)
						UNITS		"ms"
						MAX-ACCESS read-write
						STATUS     current
						DESCRIPTION
					        	"Beacon frame interval.(Range25 - 1000ms)"
						::= { dot11NewWtpWirelessIfConfigEntry 3 }

NewwtpWirelessIfDtimIntvl				OBJECT-TYPE
						SYNTAX     INTEGER(1..15)
						MAX-ACCESS read-write
						STATUS     current
						DESCRIPTION
					        	"DTIM interval."
						::= { dot11NewWtpWirelessIfConfigEntry 4 }


NewwtpWirelessIfShtRetryThld			OBJECT-TYPE
						SYNTAX     INTEGER(0..15)
						MAX-ACCESS read-write
						STATUS     current
						DESCRIPTION
					        	"The total times that retry times when frame length less than RTS threshold  ."
						::= { dot11NewWtpWirelessIfConfigEntry 5 }

NewwtpWirelessIfLongRetryThld			OBJECT-TYPE
						SYNTAX     INTEGER(1..15)
						MAX-ACCESS read-write
						STATUS     current
						DESCRIPTION
					        	"The total times that retry times when frame length over RTS threshold  ."
						::= { dot11NewWtpWirelessIfConfigEntry 6}

NewwtpWirelessIfMaxRxLifetime			OBJECT-TYPE
						SYNTAX     Unsigned32
						MAX-ACCESS read-write
						STATUS     current
						DESCRIPTION
					        	"Received data packets lifetime(units ms)."
						::= { dot11NewWtpWirelessIfConfigEntry 7 }

NewWtpPreambleLen			        OBJECT-TYPE
						SYNTAX     INTEGER{
                                                                  long(1),
                                                                  short(2)
                                                                  }           
						MAX-ACCESS read-write
						STATUS     current
						DESCRIPTION
					        	"AP PreambleLen."
						::= { dot11NewWtpWirelessIfConfigEntry 8 }

NewRtsThreshold			                OBJECT-TYPE
						SYNTAX     Integer32 
						MAX-ACCESS read-write
						STATUS     current
						DESCRIPTION
					        	"RtsThreshold."
						::= { dot11NewWtpWirelessIfConfigEntry 9 }

NewFragThreshlod			        OBJECT-TYPE
						SYNTAX     Integer32 
						MAX-ACCESS read-write
						STATUS     current
						DESCRIPTION
					        	"NewFragThreshlod."
						::= { dot11NewWtpWirelessIfConfigEntry 10 }
--**********************************************************************************************
dot11WtpEndStaInfoTable OBJECT-TYPE
	    SYNTAX      SEQUENCE OF Dot11WtpEndStaInfoEntry
	    MAX-ACCESS  not-accessible
	    STATUS      current
	    DESCRIPTION
	        "This table shows end station information."
	    ::= { wtpStation 2 }

dot11WtpEndStaInfoEntry  OBJECT-TYPE
    SYNTAX      Dot11WtpEndStaInfoEntry
    MAX-ACCESS  not-accessible
    STATUS      current
    DESCRIPTION
        "End station information."
    INDEX { wtpMacAddr
		,wtpStaMacAddr }
    ::= { dot11WtpEndStaInfoTable 1 }

Dot11WtpEndStaInfoEntry ::=SEQUENCE{
	wtpEndWMMSta		INTEGER,
	wtpStaIPAddress		IpAddress,
	wtpStaRadioMode		INTEGER,
	wtpStaRadioChannel	INTEGER,
	wtpAPTxRates		INTEGER,
	wtpStaPowerSaveMode	INTEGER,
	wtpStaVlanId		INTEGER,
	wtpStaSSIDName		DisplayString,
	wtpStaAuthenMode	INTEGER,
	wtpStaSecurityCiphers	INTEGER,
        wtpAuthenModel          INTEGER,
        wtpSecurityCiphers      INTEGER,
        apEndStaID              INTEGER,
	wtpStaIPV6Address	InetAddressIPv6
} 
wtpEndWMMSta		OBJECT-TYPE
			SYNTAX     INTEGER
			MAX-ACCESS read-only
			STATUS     current
			DESCRIPTION
				"End station WMM property."
			::= { dot11WtpEndStaInfoEntry 1 }

wtpStaIPAddress		OBJECT-TYPE
			SYNTAX     IpAddress
			MAX-ACCESS read-only
			STATUS     current
			DESCRIPTION
				"End station IP address."
			::= { dot11WtpEndStaInfoEntry 2 }

wtpStaRadioMode		OBJECT-TYPE
			SYNTAX     INTEGER{
						   a(1),
						   b(2),
						   g(4),
						   bg(6),
						   an(8),
						   aan(9),
						   gn(16),
						   ggn(20),
						   bggn(22)
						}
			MAX-ACCESS read-only
			STATUS     current
			DESCRIPTION
				"End station wireless mode(All the above base on the 802.11 standard)."
			::= { dot11WtpEndStaInfoEntry 3 }

wtpStaRadioChannel	OBJECT-TYPE
			SYNTAX     INTEGER
			MAX-ACCESS read-only
			STATUS     current
			DESCRIPTION
				"Channel that end station used."
			::= { dot11WtpEndStaInfoEntry 4 }

wtpAPTxRates		OBJECT-TYPE
			SYNTAX     INTEGER
			MAX-ACCESS read-only
			STATUS     current
			DESCRIPTION
				"End station current login rate."
			::= { dot11WtpEndStaInfoEntry 5 }

wtpStaPowerSaveMode	OBJECT-TYPE
			SYNTAX     INTEGER{
					active(1),
					powersave(2)
					}
			MAX-ACCESS read-only
			STATUS     current
			DESCRIPTION
				"End station power save mode."
			::= { dot11WtpEndStaInfoEntry 6 }

wtpStaVlanId		OBJECT-TYPE
			SYNTAX     INTEGER
			MAX-ACCESS read-only
			STATUS     current
			DESCRIPTION
				"Vlan ID that end station connect in."
			::= { dot11WtpEndStaInfoEntry 7 }

wtpStaSSIDName		OBJECT-TYPE
			SYNTAX     DisplayString
			MAX-ACCESS read-only
			STATUS     current
			DESCRIPTION
				"SSID name."
			::= { dot11WtpEndStaInfoEntry 8 }

wtpStaAuthenMode	OBJECT-TYPE
			SYNTAX     INTEGER{
					opensystem(1),
					sharedkey(2)
					}
			MAX-ACCESS read-only
			STATUS     current
			DESCRIPTION
				"Authentication mode."
			::= { dot11WtpEndStaInfoEntry 9 }

wtpStaSecurityCiphers	OBJECT-TYPE
			SYNTAX     INTEGER{
					none(1),
					Wpa(2),
					Wpa2(3),
					Wapi(4)
					}
			MAX-ACCESS read-only
			STATUS     current
			DESCRIPTION
				"Encryption mode."
			::= { dot11WtpEndStaInfoEntry 10 }

wtpAuthenModel	OBJECT-TYPE
			SYNTAX     INTEGER{
					none(1),
					PSK(2),
					Radius(3),
					WAPI-CER(4)
					}
			MAX-ACCESS read-only
			STATUS     current
			DESCRIPTION
				"wtpAuthenModel."
			::= { dot11WtpEndStaInfoEntry 11 }

wtpSecurityCiphers OBJECT-TYPE
                         SYNTAX    INTEGER{
                                            none(1),
                                            wep40(2),
                                            wep104(3),
                                            tkip(4),
                                            aesccmp(5),
                                            wpi-SMS4(6)
                                           }
                        MAX-ACCESS read-only
			STATUS     current
			DESCRIPTION
				"wtpSecurityCiphers."
			::= { dot11WtpEndStaInfoEntry 12}

apEndStaID        OBJECT-TYPE
                        SYNTAX    INTEGER
                        MAX-ACCESS read-only
			STATUS     current
			DESCRIPTION
				"apID."
			::= { dot11WtpEndStaInfoEntry 13}

wtpStaIPV6Address			OBJECT-TYPE
					SYNTAX     InetAddressIPv6
					MAX-ACCESS read-only
					STATUS     current
					DESCRIPTION
				        	"The Station IPV6Address."
					::= { dot11WtpEndStaInfoEntry 17 }
			
--**********************************************************************************************
dot11BssStaInfoTable OBJECT-TYPE
	    SYNTAX      SEQUENCE OF Dot11BssStaInfoEntry
	    MAX-ACCESS  not-accessible
	    STATUS      current
	    DESCRIPTION
	        "This table shows station information for each BSS."
	    ::= { wtpStation 3 }

dot11BssStaInfoEntry  OBJECT-TYPE
    SYNTAX      Dot11BssStaInfoEntry
    MAX-ACCESS  not-accessible
    STATUS      current
    DESCRIPTION
        "BSS station information."
    INDEX { wtpMacAddr,
    	    wtpWirelessIfIndex,
    	    NewWirelessWlanID,
    	    StaMAC}
    ::= { dot11BssStaInfoTable 1 }

Dot11BssStaInfoEntry ::=SEQUENCE{
	StaMAC			DisplayString,
	StaESSID		DisplayString,
	StaIPAddress		IpAddress
} 
StaMAC			OBJECT-TYPE
			SYNTAX     DisplayString
			MAX-ACCESS read-only
			STATUS     current
			DESCRIPTION
				"station MAC address."
			::= { dot11BssStaInfoEntry 1 }

StaESSID		OBJECT-TYPE
			SYNTAX     DisplayString
			MAX-ACCESS read-only
			STATUS     current
			DESCRIPTION
				"station access ESSID."
			::= { dot11BssStaInfoEntry 2 }

StaIPAddress		OBJECT-TYPE
			SYNTAX     IpAddress
			MAX-ACCESS read-only
			STATUS     current
			DESCRIPTION
				"station IP address."
			::= { dot11BssStaInfoEntry 3 }

			

dot11WtpWifiPositionPublicInfoTable OBJECT-TYPE
	    SYNTAX      SEQUENCE OF Dot11WtpWifiPositionPublicInfoEntry
	    MAX-ACCESS  not-accessible
	    STATUS      current
	    DESCRIPTION
	        "This table shows wtp station wifi position public information."
	    ::= { wtpStation 6 }

dot11WtpWifiPositionPublicInfoEntry  OBJECT-TYPE
    SYNTAX      Dot11WtpWifiPositionPublicInfoEntry
    MAX-ACCESS  not-accessible
    STATUS      current
    DESCRIPTION
        "wifi position information."
    INDEX { wtpMacAddr
    	    ,  WifiPositionFrequency }
    ::= { dot11WtpWifiPositionPublicInfoTable 1 }

Dot11WtpWifiPositionPublicInfoEntry ::=SEQUENCE{
	WifiPositionFrequency			INTEGER,
        wtpWifiPositionServerIp			IpAddress,
        wtpWifiPositionServerPort		INTEGER,
        wtpWifiPositionScanInterval		INTEGER,
        wtpWifiPositionScanTime			INTEGER,
        wtpWifiPositionScanChannel		Counter64,
        wtpWifiPositionScanType			INTEGER,
        wtpWifiPositionDataReportInterval	INTEGER,
        wtpWifiPositionRssiThreshold		INTEGER,
        wtpWifiPositionScanSwitch		INTEGER,
        wtpWifiPositionVersion		INTEGER,
        wtpWifiPositionFilter		INTEGER	
} 
WifiPositionFrequency			OBJECT-TYPE
					SYNTAX     INTEGER(0..1)
					MAX-ACCESS read-only
					STATUS     current
					DESCRIPTION
						"wifi position frequency, 0 means 2.4G, 1 means 5.8G."
					::= { dot11WtpWifiPositionPublicInfoEntry 1 }

wtpWifiPositionServerIp			OBJECT-TYPE
					SYNTAX     IpAddress
					MAX-ACCESS read-write
					STATUS     current
					DESCRIPTION
						"wtp wifi position server ip."
					::= { dot11WtpWifiPositionPublicInfoEntry 2 }
			
wtpWifiPositionServerPort		OBJECT-TYPE
					SYNTAX     INTEGER(1..65535)
					MAX-ACCESS read-write
					STATUS     current
					DESCRIPTION
						"wtp wifi position server port."
					::= { dot11WtpWifiPositionPublicInfoEntry 3 }

wtpWifiPositionScanInterval		OBJECT-TYPE
					SYNTAX     INTEGER(0..2000)
					MAX-ACCESS read-write
					STATUS     current
					DESCRIPTION
						"wtp wifi position scan interval.(unit:ms)"
					::= { dot11WtpWifiPositionPublicInfoEntry 4 }	
				
wtpWifiPositionScanTime			OBJECT-TYPE
					SYNTAX     INTEGER(1..2000)
					MAX-ACCESS read-write
					STATUS     current
					DESCRIPTION
						"wtp wifi position scan time.(unit:ms)"
					::= { dot11WtpWifiPositionPublicInfoEntry 5 }
				
wtpWifiPositionScanChannel		OBJECT-TYPE
					SYNTAX     Counter64
					MAX-ACCESS read-write
					STATUS     current
					DESCRIPTION
						"wtp wifi position scan channel, default scan all channel."
					::= { dot11WtpWifiPositionPublicInfoEntry 6 }	
				
wtpWifiPositionScanType			OBJECT-TYPE
					SYNTAX     INTEGER{
							  	All(0),
								Associate(1),
								NonAssociated(2)
							  }
					MAX-ACCESS read-write
					STATUS     current
					DESCRIPTION
						"wtp wifi position scan type, default type is all."
					::= { dot11WtpWifiPositionPublicInfoEntry 7 }	
				
wtpWifiPositionDataReportInterval	OBJECT-TYPE
					SYNTAX     INTEGER(1000..20000) 
					MAX-ACCESS read-write
					STATUS     current
					DESCRIPTION
						"wtp wifi position data report interval.(unit:ms)"
					::= { dot11WtpWifiPositionPublicInfoEntry 8 }	
					
wtpWifiPositionRssiThreshold		OBJECT-TYPE
					SYNTAX     INTEGER(0..95)
					MAX-ACCESS read-write
					STATUS     current
					DESCRIPTION
						"wtp wifi position rssi threshold."
					::= { dot11WtpWifiPositionPublicInfoEntry 9 }
					
wtpWifiPositionScanSwitch		OBJECT-TYPE
					SYNTAX     INTEGER{
							  	off(0),
								on(1)
							  }
					MAX-ACCESS read-write
					STATUS     current
					DESCRIPTION
						"wtp wifi position scan switch."
					::= { dot11WtpWifiPositionPublicInfoEntry 10 }	
					
wtpWifiPositionVersion		OBJECT-TYPE
					SYNTAX     INTEGER(0..1000)
					MAX-ACCESS read-write
					STATUS     current
					DESCRIPTION
						"wtp wifi position software version."
					::= { dot11WtpWifiPositionPublicInfoEntry 11 }	
					
wtpWifiPositionFilter		OBJECT-TYPE
					SYNTAX     INTEGER{
							  						off(0),
														on(1)
							  						}
					MAX-ACCESS read-write
					STATUS     current
					DESCRIPTION
						"wtp wifi position filter switch."
					::= { dot11WtpWifiPositionPublicInfoEntry 12 }	
					
--**********************************************************************************************
dot11WifiPositionGlobalInfoTable OBJECT-TYPE
	    SYNTAX      SEQUENCE OF Dot11WifiPositionGlobalInfoEntry
	    MAX-ACCESS  not-accessible
	    STATUS      current
	    DESCRIPTION
	        "This table shows wifi position global information."
	    ::= { wtpStation 7 }

dot11WifiPositionGlobalInfoEntry  OBJECT-TYPE
    SYNTAX      Dot11WifiPositionGlobalInfoEntry
    MAX-ACCESS  not-accessible
    STATUS      current
    DESCRIPTION
        "wifi position global information."
    INDEX { WifiPositionFrequency }
    ::= { dot11WifiPositionGlobalInfoTable 1 }

Dot11WifiPositionGlobalInfoEntry ::=SEQUENCE{
        WifiPositionGlobalPara			DisplayString,
        WifiPositionGlobalScanSwitch		INTEGER
} 
WifiPositionGlobalPara			OBJECT-TYPE
					SYNTAX     DisplayString
					MAX-ACCESS read-write
					STATUS     current
					DESCRIPTION
						"wifi position global parameter."
					::= { dot11WifiPositionGlobalInfoEntry 1 }

WifiPositionGlobalScanSwitch		OBJECT-TYPE
					SYNTAX     INTEGER{
							  	off(0),
								on(1)
							  }
					MAX-ACCESS read-write
					STATUS     current
					DESCRIPTION
						"wifi position global scan switch."
					::= { dot11WifiPositionGlobalInfoEntry 2 }
																																
									


			
dot11WtpWAPIPerformanceStatsTable OBJECT-TYPE
	    SYNTAX      SEQUENCE OF Dot11WtpWAPIPerformanceStatsEntry
	    MAX-ACCESS  not-accessible
	    STATUS      current
	    DESCRIPTION
	        "This table shows AP WAPI performance statistics information."
	    ::= { wtpWAPI 4 }

dot11WtpWAPIPerformanceStatsEntry  OBJECT-TYPE
    SYNTAX      Dot11WtpWAPIPerformanceStatsEntry
    MAX-ACCESS  not-accessible
    STATUS      current
    DESCRIPTION
        "AP WAPI performance stats information."
    INDEX { staMacAddr }
    ::= { dot11WtpWAPIPerformanceStatsTable 1 }

Dot11WtpWAPIPerformanceStatsEntry ::=SEQUENCE{
                staMacAddr                              DisplayString,
		wtpWapiVersion				INTEGER,
		wtpWapiControlledPortStatus		TruthValue,
		wtpWapiSelectedUnicastCipher		DisplayString,
		wtpWapiWPIReplayCounters		Counter32,
		wtpWapiWPIDecryptableErrors		Counter32,
		wtpWapiWPIMICErrors			Counter32,
		wtpWapiWAISignatureErrors		Counter32,
		wtpWapiWAIHMACErrors			Counter32,
		wtpWapiWAIAuthResultFailures		Counter32,
		wtpWapiWAIDiscardCounters		Counter32,
		wtpWapiWAITimeoutCounters		Counter32,
		wtpWapiWAIFormatErrors			Counter32,
		wtpWapiWAICertificateHandshakeFailures	Counter32,
		wtpWapiWAIUnicastHandshakeFailures	Counter32,
		wtpWapiWAIMulticastHandshakeFailures	Counter32
}
staMacAddr				OBJECT-TYPE
					SYNTAX     DisplayString
					MAX-ACCESS read-only
					STATUS     current
					DESCRIPTION
						"staMacAddr."
					::= { dot11WtpWAPIPerformanceStatsEntry 1 }
					
wtpWapiVersion				OBJECT-TYPE
					SYNTAX     INTEGER
					MAX-ACCESS read-only
					STATUS     current
					DESCRIPTION
						"Wapi version."
					::= { dot11WtpWAPIPerformanceStatsEntry 2 }

wtpWapiControlledPortStatus		OBJECT-TYPE
					SYNTAX     TruthValue
					MAX-ACCESS read-only
					STATUS     current
					DESCRIPTION
						"Authentication controled port status."
					::= { dot11WtpWAPIPerformanceStatsEntry 3 }

wtpWapiSelectedUnicastCipher		OBJECT-TYPE
					SYNTAX     DisplayString
					MAX-ACCESS read-only
					STATUS     current
					DESCRIPTION
						"Selected unicast encryption cipher."
					::= { dot11WtpWAPIPerformanceStatsEntry 4 }

wtpWapiWPIReplayCounters			OBJECT-TYPE
					SYNTAX     Counter32
					MAX-ACCESS read-only
					STATUS     current
					DESCRIPTION
						"The amount of WPI MPDU which droped because of response response mechanism."
					::= { dot11WtpWAPIPerformanceStatsEntry 5 }

wtpWapiWPIDecryptableErrors		OBJECT-TYPE
					SYNTAX     Counter32
					MAX-ACCESS read-only
					STATUS     current
					DESCRIPTION
						"The amount of WPI MPDU which droped because of invalid key."
					::= { dot11WtpWAPIPerformanceStatsEntry 6 }

wtpWapiWPIMICErrors			OBJECT-TYPE
					SYNTAX     Counter32
					MAX-ACCESS read-only
					STATUS     current
					DESCRIPTION
						"The amount of WPI MPDU which droped because of mic check failure."
					::= { dot11WtpWAPIPerformanceStatsEntry 7 }

wtpWapiWAISignatureErrors			OBJECT-TYPE
					SYNTAX     Counter32
					MAX-ACCESS read-only
					STATUS     current
					DESCRIPTION
						"The amount of WAI data packets of signed error."
					::= { dot11WtpWAPIPerformanceStatsEntry 8 }

wtpWapiWAIHMACErrors			OBJECT-TYPE
					SYNTAX     Counter32
					MAX-ACCESS read-only
					STATUS     current
					DESCRIPTION
						"Authentication key WAI validation failure the number of packets."
					::= { dot11WtpWAPIPerformanceStatsEntry 9 }

wtpWapiWAIAuthResultFailures		OBJECT-TYPE
					SYNTAX     Counter32
					MAX-ACCESS read-only
					STATUS     current
					DESCRIPTION
						"The number of WAI failed authentication."
					::= { dot11WtpWAPIPerformanceStatsEntry 10 }

wtpWapiWAIDiscardCounters		OBJECT-TYPE
					SYNTAX     Counter32
					MAX-ACCESS read-only
					STATUS     current
					DESCRIPTION
						"The number of WAI packets discarded."
					::= { dot11WtpWAPIPerformanceStatsEntry 11 }

wtpWapiWAITimeoutCounters		OBJECT-TYPE
					SYNTAX     Counter32
					MAX-ACCESS read-only
					STATUS     current
					DESCRIPTION
						"The number of WAI overtime packet."
					::= { dot11WtpWAPIPerformanceStatsEntry 12 }

wtpWapiWAIFormatErrors			OBJECT-TYPE
					SYNTAX     Counter32
					MAX-ACCESS read-only
					STATUS     current
					DESCRIPTION
						"WAI malformed packet number."
					::= { dot11WtpWAPIPerformanceStatsEntry 13 }

wtpWapiWAICertificateHandshakeFailures	OBJECT-TYPE
					SYNTAX     Counter32
					MAX-ACCESS read-only
					STATUS     current
					DESCRIPTION
						"WAI failed to shake hands with the number of certified."
					::= { dot11WtpWAPIPerformanceStatsEntry 14 }

wtpWapiWAIUnicastHandshakeFailures	OBJECT-TYPE
					SYNTAX     Counter32
					MAX-ACCESS read-only
					STATUS     current
					DESCRIPTION
						"WAI unicast number of the failure of key agreement."
					::= { dot11WtpWAPIPerformanceStatsEntry 15 }

wtpWapiWAIMulticastHandshakeFailures	OBJECT-TYPE
					SYNTAX     Counter32
					MAX-ACCESS read-only
					STATUS     current
					DESCRIPTION
						"WAI multicast number of key failure."
					::= { dot11WtpWAPIPerformanceStatsEntry 16 }

--dot11WAPIBasicConfigTable 	OBJECT-TYPE
--			    	SYNTAX      SEQUENCE OF Dot11WAPIBasicConfigEntry
--			    	MAX-ACCESS  not-accessible
--			    	STATUS      current
--			    	DESCRIPTION
--			        	"This table shows WAPI basic config information."
--			    	::= { wtpWAPI 8 }

--dot11WAPIBasicConfigEntry  	OBJECT-TYPE
--    				SYNTAX      Dot11WAPIBasicConfigEntry
--				MAX-ACCESS  not-accessible
--				STATUS      current
--				DESCRIPTION
--				     "WAPI basic config information."
--				INDEX { wapiASIPAddress }
--				::= { dot11WAPIBasicConfigTable 1 }

--Dot11WAPIBasicConfigEntry ::=SEQUENCE{
--		wapiASIPAddress		IpAddress,
--		wapiIsInstalledCer	TruthValue
--}
--wapiASIPAddress				OBJECT-TYPE
--					SYNTAX     IpAddress
--					MAX-ACCESS read-write
--					STATUS     current
--					DESCRIPTION
--						"."
--					::= { dot11WAPIBasicConfigEntry 1 }

--wapiIsInstalledCer			OBJECT-TYPE
--					SYNTAX     TruthValue
--					MAX-ACCESS read-only
--					STATUS     current
--					DESCRIPTION
--						"."
--					::= { dot11WAPIBasicConfigEntry 2 }

dot11BSSIDWAPIProtocolConfigTable 	OBJECT-TYPE
			    	SYNTAX      SEQUENCE OF Dot11BSSIDWAPIProtocolConfigEntry
			    	MAX-ACCESS  not-accessible
			    	STATUS      current
			    	DESCRIPTION
			        	"This table shows WAPI protocol config information."
			    	::= { wtpWAPI 2 }

dot11BSSIDWAPIProtocolConfigEntry  	OBJECT-TYPE
    				SYNTAX      Dot11BSSIDWAPIProtocolConfigEntry
				MAX-ACCESS  not-accessible
				STATUS      current
				DESCRIPTION
				     "WAPI protocol config information."
				INDEX { wtpMacAddr,wtpBssCurrID }
				::= { dot11BSSIDWAPIProtocolConfigTable 1 }

Dot11BSSIDWAPIProtocolConfigEntry ::=SEQUENCE{
		wapiControlledAuthControl		TruthValue,
		wapiControlledPortControl		INTEGER,
		wapiEnabled				TruthValue,
		wapiCertificateUpdateCount		Unsigned32,
		wapiMulticastUpdateCount		Unsigned32,
		wapiUnicastUpdateCount		Unsigned32,
		wapiAuthSuiteSelected		INTEGER,
		wapiAuthSuiteRequested		INTEGER

}

wapiControlledAuthControl		OBJECT-TYPE
					SYNTAX     TruthValue
					MAX-ACCESS read-only
					STATUS     current
					DESCRIPTION
						"Whether using uthorization."
					::= { dot11BSSIDWAPIProtocolConfigEntry 1 }

wapiControlledPortControl		OBJECT-TYPE
					SYNTAX     INTEGER{
							Auto(0),
							Forceunautherized(1)
							}
					MAX-ACCESS read-only
					STATUS     current
					DESCRIPTION
						"Port control type."
					::= { dot11BSSIDWAPIProtocolConfigEntry 2 }

wapiEnabled				OBJECT-TYPE
					SYNTAX     TruthValue
					MAX-ACCESS read-write
					STATUS     current
					DESCRIPTION
						"Whether using wapi."
					::= { dot11BSSIDWAPIProtocolConfigEntry 3 }


wapiCertificateUpdateCount		OBJECT-TYPE
					SYNTAX     Unsigned32
					MAX-ACCESS read-write
					STATUS     current
					DESCRIPTION
						"Authentication handshake retry times."
					::= { dot11BSSIDWAPIProtocolConfigEntry 4 }

wapiMulticastUpdateCount		OBJECT-TYPE
					SYNTAX     Unsigned32
					MAX-ACCESS read-write
					STATUS     current
					DESCRIPTION
						"MSK handshake retry times."
					::= { dot11BSSIDWAPIProtocolConfigEntry 5 }

wapiUnicastUpdateCount			OBJECT-TYPE
					SYNTAX     Unsigned32
					MAX-ACCESS read-write
					STATUS     current
					DESCRIPTION
						"Unicast handshake retry key times."
					::= { dot11BSSIDWAPIProtocolConfigEntry 6 }


wapiAuthSuiteSelected		OBJECT-TYPE
					SYNTAX     INTEGER
					MAX-ACCESS read-only
					STATUS     current
					DESCRIPTION
						"AKM selected."
					::= { dot11BSSIDWAPIProtocolConfigEntry 7 }

wapiAuthSuiteRequested		OBJECT-TYPE
					SYNTAX     INTEGER
					MAX-ACCESS read-only
					STATUS     current
					DESCRIPTION
						"Request a choice of AKM."
					::= { dot11BSSIDWAPIProtocolConfigEntry 8 }

dot11UnicastEncryption OBJECT IDENTIFIER::={ wtpWAPI 6 }

UnicastCipher				OBJECT-TYPE
					SYNTAX     DisplayString
					MAX-ACCESS read-only
					STATUS     current
					DESCRIPTION
						"Unicast cipher."
					::= { dot11UnicastEncryption 1 }

UnicastCipherEnabled			OBJECT-TYPE
					SYNTAX     TruthValue
					MAX-ACCESS read-write
					STATUS     current
					DESCRIPTION
						"Unicast clipher enabled."
					::= { dot11UnicastEncryption 2 }

UnicastCipherSize			OBJECT-TYPE
					SYNTAX     Unsigned32
					MAX-ACCESS read-only
					STATUS     current
					DESCRIPTION
						"Unicast cipher size."
					::= { dot11UnicastEncryption 3 }


dot11AKMSuite OBJECT IDENTIFIER::={ wtpWAPI 7 }

AuthenticationSuite			OBJECT-TYPE
					SYNTAX     DisplayString
					MAX-ACCESS read-only
					STATUS     current
					DESCRIPTION
						"Authentication suite."
					::= { dot11AKMSuite 1 }

AuthenticationSuiteEnabled		OBJECT-TYPE
					SYNTAX     TruthValue
					MAX-ACCESS read-write
					STATUS     current
					DESCRIPTION
						"Whether authentication suite enabled."
					::= { dot11AKMSuite 2 }

dot11AKMConfigTable OBJECT-TYPE
	    SYNTAX      SEQUENCE OF Dot11AKMConfigEntry
	    MAX-ACCESS  not-accessible
	    STATUS      current
	    DESCRIPTION
	        "Config AKM Suite."
	    ::= { wtpWAPI 8 }

dot11AKMConfigEntry  OBJECT-TYPE
    SYNTAX      Dot11AKMConfigEntry
    MAX-ACCESS  not-accessible
    STATUS      current
    DESCRIPTION
        "Config AKM Suite."
    INDEX { AKMWlanID }
    ::= { dot11AKMConfigTable 1 }

Dot11AKMConfigEntry ::=SEQUENCE{
		AKMWlanID				INTEGER,
		AKMAuthenticationSuite		   DisplayString,
		AKMAuthenticationSuiteEnabled	      TruthValue	
}

AKMWlanID			OBJECT-TYPE
					SYNTAX     INTEGER
					MAX-ACCESS read-only
					STATUS     current
					DESCRIPTION
						"."
					::= { dot11AKMConfigEntry 1}

AKMAuthenticationSuite			OBJECT-TYPE
					SYNTAX     DisplayString
					MAX-ACCESS read-only
					STATUS     current
					DESCRIPTION
						"."
					::= { dot11AKMConfigEntry 2 }

AKMAuthenticationSuiteEnabled		OBJECT-TYPE
					SYNTAX     TruthValue
					MAX-ACCESS read-write
					STATUS     current
					DESCRIPTION
						"."
					::= { dot11AKMConfigEntry 3}

dot11UnicastTable OBJECT-TYPE
	    SYNTAX      SEQUENCE OF Dot11UnicastEntry
	    MAX-ACCESS  not-accessible
	    STATUS      current
	    DESCRIPTION
	        "Config Unicast Suite."
	    ::= { wtpWAPI 9 }

dot11UnicastEntry  OBJECT-TYPE
    SYNTAX      Dot11UnicastEntry
    MAX-ACCESS  not-accessible
    STATUS      current
    DESCRIPTION
        "Config Unicast Suite."
    INDEX { UnicastWlanID }
    ::= { dot11UnicastTable 1 }

Dot11UnicastEntry ::=SEQUENCE{
		UnicastWlanID				INTEGER,
		NewUnicastCipher		   DisplayString,
		NewUnicastCipherEnabled	      TruthValue,
                NewUnicastCipherSize	      Unsigned32
}
UnicastWlanID				OBJECT-TYPE
					SYNTAX     INTEGER
					MAX-ACCESS read-only
					STATUS     current
					DESCRIPTION
						"."
					::= { dot11UnicastEntry 1}

NewUnicastCipher				OBJECT-TYPE
					SYNTAX     DisplayString
					MAX-ACCESS read-only
					STATUS     current
					DESCRIPTION
						"."
					::= { dot11UnicastEntry 2 }

NewUnicastCipherEnabled			OBJECT-TYPE
					SYNTAX     TruthValue
					MAX-ACCESS read-write
					STATUS     current
					DESCRIPTION
						"."
					::= { dot11UnicastEntry 3 }

NewUnicastCipherSize			OBJECT-TYPE
					SYNTAX     Unsigned32
					MAX-ACCESS read-only
					STATUS     current
					DESCRIPTION
						"."
					::= { dot11UnicastEntry 4}


dot11WtpWAPIConfigTable OBJECT-TYPE
	    SYNTAX      SEQUENCE OF Dot11WtpWAPIConfigEntry
	    MAX-ACCESS  not-accessible
	    STATUS      current
	    DESCRIPTION
	        "This table shows AP WAPI Config information."
	    ::= { wtpWAPI 10 }

dot11WtpWAPIConfigEntry  OBJECT-TYPE
    SYNTAX      Dot11WtpWAPIConfigEntry
    MAX-ACCESS  not-accessible
    STATUS      current
    DESCRIPTION
        "AP WAPI performance config information."
    INDEX { WapiWlanID }
    ::= { dot11WtpWAPIConfigTable 1 }

Dot11WtpWAPIConfigEntry ::=SEQUENCE{
                WapiWlanID                              INTEGER,
		wtpWapiConfigVersion		        Integer32,
		wtpWapiControlledAuthenControlenabled	TruthValue,
		wtpWapiControlledPortControl		DisplayString,
		wtpWapiWPIOptionImplement		TruthValue,
		wtpWapiWPIPreauthImplemented 		TruthValue,
		wtpWapiEnabled			        TruthValue,
		wtpWapiPreauthEnabled 		        TruthValue,
                wtpWapiUnicastKeysSupported             Unsigned32,
		wtpWapiUnicastRekeyMethod 		INTEGER,
		wtpWapiUnicastRekeyTime 		Unsigned32,
		wtpWapiUnicastRekeyPackets 		Unsigned32,
		wtpWapiMulticastCipher 		        DisplayString,
		wtpWapiMulticastRekeyMethod 	        INTEGER,
		wtpWapiMulticastRekeyTime 	        Unsigned32,
		wtpWapiMulticastRekeyPackets 	        Unsigned32,
		wtpWapiMulticastRekeyStrict	        TruthValue,
                wtpWapiPSKValue                         DisplayString,
                wtpWapiPSKPassPhrase                    DisplayString,
                wtpWapiCertificateUpdateCount           Unsigned32,
                wtpWapiMulticastUpdateCount             Unsigned32,
                wtpWapiUnicastUpdateCount               Unsigned32,
                wtpWapiMulticastCipherSize              Unsigned32,
                wtpWapiBKLifetime                       Unsigned32,
                wtpWapiBKReauthThreshold                Unsigned32,
                wtpWapiSATimeout                        Unsigned32,
                wtpWapiAuthSuiteSelected                DisplayString,
                wtpWapiUnicastCipherSelected            DisplayString,
                wtpWapiMulticastCipherSelected          DisplayString,
                wtpWapiBKIDUsed                         DisplayString,
                wtpWapiAuthSuiteRequested               DisplayString,
                wtpWapiUnicastCipherRequested           DisplayString,
                wtpWapiMulticastCipherRequested         DisplayString
}
WapiWlanID		                OBJECT-TYPE
					SYNTAX     INTEGER
					MAX-ACCESS read-only
					STATUS     current
					DESCRIPTION
						"WapiWlanID."
					::= { dot11WtpWAPIConfigEntry 1 }
wtpWapiConfigVersion		                OBJECT-TYPE
					SYNTAX     Integer32
					MAX-ACCESS read-only
					STATUS     current
					DESCRIPTION
						"wtpWapiConfigVersion."
					::= { dot11WtpWAPIConfigEntry 2 }
wtpWapiControlledAuthenControlenabled	OBJECT-TYPE
					SYNTAX     TruthValue
					MAX-ACCESS read-only
					STATUS     current
					DESCRIPTION
						"wtpWapiControlledAuthenControlenabled."
					::= { dot11WtpWAPIConfigEntry 3 }
wtpWapiControlledPortControl		OBJECT-TYPE
					SYNTAX     DisplayString
					MAX-ACCESS read-only
					STATUS     current
					DESCRIPTION
						"wtpWapiControlledPortControl."
					::= { dot11WtpWAPIConfigEntry 4 }
wtpWapiWPIOptionImplement		OBJECT-TYPE
					SYNTAX     TruthValue
					MAX-ACCESS read-only
					STATUS     current
					DESCRIPTION
						"wtpWapiWPIOptionImplement."
					::= { dot11WtpWAPIConfigEntry 5 }
wtpWapiWPIPreauthImplemented		OBJECT-TYPE
					SYNTAX     TruthValue
					MAX-ACCESS read-only
					STATUS     current
					DESCRIPTION
						"wtpWapiWPIPreauthImplemented."
					::= { dot11WtpWAPIConfigEntry 6 }
wtpWapiEnabled		                OBJECT-TYPE
					SYNTAX     TruthValue
					MAX-ACCESS read-write
					STATUS     current
					DESCRIPTION
						"wtpWapiEnabled."
					::= { dot11WtpWAPIConfigEntry 7 }
wtpWapiPreauthEnabled		        OBJECT-TYPE
					SYNTAX     TruthValue
					MAX-ACCESS read-write
					STATUS     current
					DESCRIPTION
						"wtpWapiPreauthEnabled."
					::= { dot11WtpWAPIConfigEntry 8 }
wtpWapiUnicastKeysSupported		OBJECT-TYPE
					SYNTAX     Unsigned32
					MAX-ACCESS read-only
					STATUS     current
					DESCRIPTION
						"wtpWapiUnicastKeysSupported."
					::= { dot11WtpWAPIConfigEntry 9 }
wtpWapiUnicastRekeyMethod		OBJECT-TYPE
					SYNTAX     INTEGER{
                                                          disabled(1),
                                                          timeBased(2),
                                                          packetBased(3),
                                                          timepacket-Based(4)                                                                            
                                                          }
					MAX-ACCESS read-write
					STATUS     current
					DESCRIPTION
						"wtpWapiUnicastKeysSupported."
					::= { dot11WtpWAPIConfigEntry 10 }
wtpWapiUnicastRekeyTime		        OBJECT-TYPE
					SYNTAX     Unsigned32
					MAX-ACCESS read-write
					STATUS     current
					DESCRIPTION
						"wtpWapiUnicastRekeyTime."
					::= { dot11WtpWAPIConfigEntry 11 }
wtpWapiUnicastRekeyPackets		OBJECT-TYPE
					SYNTAX     Unsigned32
					MAX-ACCESS read-write
					STATUS     current
					DESCRIPTION
						"wtpWapiUnicastRekeyPackets."
					::= { dot11WtpWAPIConfigEntry 12 }
wtpWapiMulticastCipher		        OBJECT-TYPE
					SYNTAX     DisplayString
					MAX-ACCESS read-write
					STATUS     current
					DESCRIPTION
						"wtpWapiMulticastCipher."
					::= { dot11WtpWAPIConfigEntry 13 }
wtpWapiMulticastRekeyMethod		OBJECT-TYPE
					SYNTAX     INTEGER{
							disable(1),
							time-based(2),
							packet-based(3),
							both-based(4)
							}
					MAX-ACCESS read-write
					STATUS     current
					DESCRIPTION
						"wtpWapiMulticastRekeyMethod."
					::= { dot11WtpWAPIConfigEntry 14 }
wtpWapiMulticastRekeyTime		OBJECT-TYPE
					SYNTAX     Unsigned32
					MAX-ACCESS read-write
					STATUS     current
					DESCRIPTION
						"wtpWapiMulticastRekeyTime."
					::= { dot11WtpWAPIConfigEntry 15 }
wtpWapiMulticastRekeyPackets		OBJECT-TYPE
					SYNTAX     Unsigned32
					MAX-ACCESS read-write
					STATUS     current
					DESCRIPTION
						"wtpWapiMulticastRekeyPackets."
					::= { dot11WtpWAPIConfigEntry 16 }
wtpWapiMulticastRekeyStrict		OBJECT-TYPE
					SYNTAX     TruthValue
					MAX-ACCESS read-write
					STATUS     current
					DESCRIPTION
						"wtpWapiMulticastRekeyStrict."
					::= { dot11WtpWAPIConfigEntry 17 }
wtpWapiPSKValue		                OBJECT-TYPE
					SYNTAX     DisplayString
					MAX-ACCESS read-write
					STATUS     current
					DESCRIPTION
						"wtpWapiPSKValue."
					::= { dot11WtpWAPIConfigEntry 18 }
wtpWapiPSKPassPhrase		        OBJECT-TYPE
					SYNTAX     DisplayString
					MAX-ACCESS read-write
					STATUS     current
					DESCRIPTION
						"wtpWapiPSKPassPhrase."
					::= { dot11WtpWAPIConfigEntry 19 }
wtpWapiCertificateUpdateCount		OBJECT-TYPE
					SYNTAX     Unsigned32
					MAX-ACCESS read-write
					STATUS     current
					DESCRIPTION
						"wtpWapiCertificateUpdateCount."
					::= { dot11WtpWAPIConfigEntry 20 }

wtpWapiMulticastUpdateCount		OBJECT-TYPE
					SYNTAX     Unsigned32
					MAX-ACCESS read-write
					STATUS     current
					DESCRIPTION
						"wtpWapiMulticastUpdateCount."
					::= { dot11WtpWAPIConfigEntry 21 }
wtpWapiUnicastUpdateCount		OBJECT-TYPE
					SYNTAX     Unsigned32
					MAX-ACCESS read-write
					STATUS     current
					DESCRIPTION
						"wtpWapiUnicastUpdateCount."
					::= { dot11WtpWAPIConfigEntry 22 }
wtpWapiMulticastCipherSize		OBJECT-TYPE
					SYNTAX     Unsigned32
					MAX-ACCESS read-only
					STATUS     current
					DESCRIPTION
						"wtpWapiMulticastCipherSize."
					::= { dot11WtpWAPIConfigEntry 23 }
wtpWapiBKLifetime		        OBJECT-TYPE
					SYNTAX     Unsigned32
					MAX-ACCESS read-write
					STATUS     current
					DESCRIPTION
						"wtpWapiBKLifetime."
					::= { dot11WtpWAPIConfigEntry 24 }
wtpWapiBKReauthThreshold		OBJECT-TYPE
					SYNTAX     Unsigned32
					MAX-ACCESS read-write
					STATUS     current
					DESCRIPTION
						"wtpWapiBKReauthThreshold."
					::= { dot11WtpWAPIConfigEntry 25 }
wtpWapiSATimeout		        OBJECT-TYPE
					SYNTAX     Unsigned32
					MAX-ACCESS read-write
					STATUS     current
					DESCRIPTION
						"wtpWapiSATimeout."
					::= { dot11WtpWAPIConfigEntry 26}
wtpWapiAuthSuiteSelected		OBJECT-TYPE
					SYNTAX     DisplayString
					MAX-ACCESS read-only
					STATUS     current
					DESCRIPTION
						"wtpWapiAuthSuiteSelected."
					::= { dot11WtpWAPIConfigEntry 27}
wtpWapiUnicastCipherSelected            OBJECT-TYPE
					SYNTAX     DisplayString
					MAX-ACCESS read-only
					STATUS     current
					DESCRIPTION
						"wtpWapiUnicastCipherSelected."
					::= { dot11WtpWAPIConfigEntry 28}
wtpWapiMulticastCipherSelected          		OBJECT-TYPE
					SYNTAX     DisplayString
					MAX-ACCESS read-only
					STATUS     current
					DESCRIPTION
						"wtpWapiMulticastCipherSelected."
					::= { dot11WtpWAPIConfigEntry 29}
wtpWapiBKIDUsed                         OBJECT-TYPE
					SYNTAX     DisplayString
					MAX-ACCESS read-only
					STATUS     current
					DESCRIPTION
						"wtpWapiBKIDUsed."
					::= { dot11WtpWAPIConfigEntry 30}
wtpWapiAuthSuiteRequested               OBJECT-TYPE
					SYNTAX     DisplayString
					MAX-ACCESS read-only
					STATUS     current
					DESCRIPTION
						"wtpWapiAuthSuiteRequested."
					::= { dot11WtpWAPIConfigEntry 31}
wtpWapiUnicastCipherRequested           		OBJECT-TYPE
					SYNTAX     DisplayString
					MAX-ACCESS read-only
					STATUS     current
					DESCRIPTION
						"wtpWapiUnicastCipherRequested."
					::= { dot11WtpWAPIConfigEntry 32}
wtpWapiMulticastCipherRequested         OBJECT-TYPE
					SYNTAX     DisplayString
					MAX-ACCESS read-only
					STATUS     current
					DESCRIPTION
						"wtpWapiMulticastCipherRequested."
					::= { dot11WtpWAPIConfigEntry 33}
--*********************************************************************************************************************************************************
dot11BssWAPIPerformanceStatsTable OBJECT-TYPE
	    SYNTAX      SEQUENCE OF Dot11BssWAPIPerformanceStatsEntry
	    MAX-ACCESS  not-accessible
	    STATUS      current
	    DESCRIPTION
	        "This table shows AP WAPI performance statistics information."
	    ::= { wtpWAPI 5 }

dot11BssWAPIPerformanceStatsEntry  OBJECT-TYPE
    SYNTAX      Dot11BssWAPIPerformanceStatsEntry
    MAX-ACCESS  not-accessible
    STATUS      current
    DESCRIPTION
        "AP WAPI performance stats information."
    INDEX { wtpMacAddr,
		wtpBssCurrID }
    ::= { dot11BssWAPIPerformanceStatsTable 1 }

Dot11BssWAPIPerformanceStatsEntry ::=SEQUENCE{
		bssWapiControlledPortStatus		TruthValue,
		bssWapiSelectedUnicastCipher		DisplayString,
		bssWapiWPIReplayCounters		Counter32,
		bssWapiWPIDecryptableErrors		Counter32,
		bssWapiWPIMICErrors			Counter32,
		bssWapiWAISignatureErrors		Counter32,
		bssWapiWAIHMACErrors			Counter32,
		bssWapiWAIAuthResultFailures		Counter32,
		bssWapiWAIDiscardCounters		Counter32,
		bssWapiWAITimeoutCounters		Counter32,
		bssWapiWAIFormatErrors			Counter32,
		bssWapiWAICertificateHandshakeFailures	Counter32,
		bssWapiWAIUnicastHandshakeFailures	Counter32,
		bssWapiWAIMulticastHandshakeFailures	Counter32
}
bssWapiControlledPortStatus		OBJECT-TYPE
					SYNTAX     TruthValue
					MAX-ACCESS read-only
					STATUS     current
					DESCRIPTION
						"Authentication controled port status."
					::= { dot11BssWAPIPerformanceStatsEntry 1 }

bssWapiSelectedUnicastCipher		OBJECT-TYPE
					SYNTAX     DisplayString
					MAX-ACCESS read-only
					STATUS     current
					DESCRIPTION
						"Selected unicast encryption cipher."
					::= { dot11BssWAPIPerformanceStatsEntry 2 }

bssWapiWPIReplayCounters			OBJECT-TYPE
					SYNTAX     Counter32
					MAX-ACCESS read-only
					STATUS     current
					DESCRIPTION
						"The amount of WPI MPDU which droped because of response response mechanism."
					::= { dot11BssWAPIPerformanceStatsEntry 3 }

bssWapiWPIDecryptableErrors		OBJECT-TYPE
					SYNTAX     Counter32
					MAX-ACCESS read-only
					STATUS     current
					DESCRIPTION
						"The amount of WPI MPDU which droped because of invalid key."
					::= { dot11BssWAPIPerformanceStatsEntry 4 }

bssWapiWPIMICErrors			OBJECT-TYPE
					SYNTAX     Counter32
					MAX-ACCESS read-only
					STATUS     current
					DESCRIPTION
						"The amount of WPI MPDU which droped because of mic check failure."
					::= { dot11BssWAPIPerformanceStatsEntry 5 }

bssWapiWAISignatureErrors			OBJECT-TYPE
					SYNTAX     Counter32
					MAX-ACCESS read-only
					STATUS     current
					DESCRIPTION
						"The amount of WAI data packets of signed error."
					::= { dot11BssWAPIPerformanceStatsEntry 6 }

bssWapiWAIHMACErrors			OBJECT-TYPE
					SYNTAX     Counter32
					MAX-ACCESS read-only
					STATUS     current
					DESCRIPTION
						"Authentication key WAI validation failure the number of packets."
					::= { dot11BssWAPIPerformanceStatsEntry 7 }

bssWapiWAIAuthResultFailures		OBJECT-TYPE
					SYNTAX     Counter32
					MAX-ACCESS read-only
					STATUS     current
					DESCRIPTION
						"The number of WAI failed authentication."
					::= { dot11BssWAPIPerformanceStatsEntry 8 }

bssWapiWAIDiscardCounters		OBJECT-TYPE
					SYNTAX     Counter32
					MAX-ACCESS read-only
					STATUS     current
					DESCRIPTION
						"The number of WAI packets discarded."
					::= { dot11BssWAPIPerformanceStatsEntry 9 }

bssWapiWAITimeoutCounters		OBJECT-TYPE
					SYNTAX     Counter32
					MAX-ACCESS read-only
					STATUS     current
					DESCRIPTION
						"The number of WAI overtime packet."
					::= { dot11BssWAPIPerformanceStatsEntry 10 }

bssWapiWAIFormatErrors			OBJECT-TYPE
					SYNTAX     Counter32
					MAX-ACCESS read-only
					STATUS     current
					DESCRIPTION
						"WAI malformed packet number."
					::= { dot11BssWAPIPerformanceStatsEntry 11 }

bssWapiWAICertificateHandshakeFailures	OBJECT-TYPE
					SYNTAX     Counter32
					MAX-ACCESS read-only
					STATUS     current
					DESCRIPTION
						"WAI failed to shake hands with the number of certified."
					::= { dot11BssWAPIPerformanceStatsEntry 12 }

bssWapiWAIUnicastHandshakeFailures	OBJECT-TYPE
					SYNTAX     Counter32
					MAX-ACCESS read-only
					STATUS     current
					DESCRIPTION
						"WAI unicast number of the failure of key agreement."
					::= { dot11BssWAPIPerformanceStatsEntry 13 }

bssWapiWAIMulticastHandshakeFailures	OBJECT-TYPE
					SYNTAX     Counter32
					MAX-ACCESS read-only
					STATUS     current
					DESCRIPTION
						"WAI multicast number of key failure."
					::= { dot11BssWAPIPerformanceStatsEntry 14 }
--*******************************************************************************************************************************************************************
dot11StaWAPIProtocolConfigTable OBJECT-TYPE
	    SYNTAX      SEQUENCE OF Dot11StaWAPIProtocolConfigEntry
	    MAX-ACCESS  not-accessible
	    STATUS      current
	    DESCRIPTION
	        "This table shows AP WAPI performance statistics information."
	    ::= { wtpWAPI 3 }

dot11StaWAPIProtocolConfigEntry  OBJECT-TYPE
    SYNTAX      Dot11StaWAPIProtocolConfigEntry
    MAX-ACCESS  not-accessible
    STATUS      current
    DESCRIPTION
        "AP WAPI performance stats information."
    INDEX { wtpMacAddr,
		wtpStaMacAddr }
    ::= { dot11StaWAPIProtocolConfigTable 1 }

Dot11StaWAPIProtocolConfigEntry ::=SEQUENCE{
		wapiBKIDUsed			DisplayString,
		wapiControlledPortStatus	TruthValue
}
wapiBKIDUsed				OBJECT-TYPE
					SYNTAX     DisplayString
					MAX-ACCESS read-only
					STATUS     current
					DESCRIPTION
						"Used BK ID."
					::= { dot11StaWAPIProtocolConfigEntry 1 }
					
wapiControlledPortStatus		OBJECT-TYPE
					SYNTAX      	TruthValue
					MAX-ACCESS  	read-only
					STATUS      	current
					DESCRIPTION
					      "The status of WAPI controlled port."
					::= { dot11StaWAPIProtocolConfigEntry 2 }
										
--*******************************************************************************************************************************************************************
wapiBasicInfo	OBJECT IDENTIFIER::={ wtpWAPI 1	}
wapiConfigVersion			OBJECT-TYPE
					SYNTAX     INTEGER
					MAX-ACCESS read-only
					STATUS     current
					DESCRIPTION
						"Wapi config version."
					::= { wapiBasicInfo 1 }

wapiOptionImplemented			OBJECT-TYPE
					SYNTAX     TruthValue
					MAX-ACCESS read-only
					STATUS     current
					DESCRIPTION
						"Wapi option implemented."
					::= { wapiBasicInfo 2 }
wapiPreauthImplemented			OBJECT-TYPE
					SYNTAX     TruthValue
					MAX-ACCESS read-only
					STATUS     current
					DESCRIPTION
						"Wapi preauth implemented."
					::= { wapiBasicInfo 3 }

wapiPreauthEnabled			OBJECT-TYPE
					SYNTAX     TruthValue
					MAX-ACCESS read-write
					STATUS     current
					DESCRIPTION
						"Whether preauth enabled."
					::= { wapiBasicInfo 4 }
wapiUnicastKeysSupported		OBJECT-TYPE
					SYNTAX     Unsigned32
					MAX-ACCESS read-only
					STATUS     current
					DESCRIPTION
						"Wapi unicase keys supported."
					::= { wapiBasicInfo 5 }

wapiMulticastCipher			OBJECT-TYPE
					SYNTAX     DisplayString
					MAX-ACCESS read-write
					STATUS     current
					DESCRIPTION
						"Wapi multicase cipher."
					::= { wapiBasicInfo 6 }

wapiMulticastRekeyStrict		OBJECT-TYPE
					SYNTAX     TruthValue
					MAX-ACCESS read-write
					STATUS     current
					DESCRIPTION
						"Wapi muliticast rekey strict."
					::= { wapiBasicInfo 7 }
wapiMulticastCipherSize			OBJECT-TYPE
					SYNTAX     Unsigned32
					MAX-ACCESS read-only
					STATUS     current
					DESCRIPTION
						"Wapi multicast cipher size."
					::= { wapiBasicInfo 8 }

wapiBKLifetime				OBJECT-TYPE
					SYNTAX     Unsigned32
					MAX-ACCESS read-write
					STATUS     current
					DESCRIPTION
						"Wapi bk life time."
					::= { wapiBasicInfo 9 }

wapiBKReauthThreshold			OBJECT-TYPE
					SYNTAX     Unsigned32
					MAX-ACCESS read-write
					STATUS     current
					DESCRIPTION
						"Wapi BK reauth threshold."
					::= { wapiBasicInfo 10 }

wapiSATimeout				OBJECT-TYPE
					SYNTAX     Unsigned32
					MAX-ACCESS read-write
					STATUS     current
					DESCRIPTION
						"The time o establish a secure connection."
					::= { wapiBasicInfo 11 }
wapiUnicastCipherSelected		OBJECT-TYPE
					SYNTAX     DisplayString
					MAX-ACCESS read-only
					STATUS     current
					DESCRIPTION
						"Wapi unicast cipher selected."
					::= { wapiBasicInfo 12 }

wapiMulticastCipherSelected		OBJECT-TYPE
					SYNTAX     DisplayString
					MAX-ACCESS read-only
					STATUS     current
					DESCRIPTION
						"Wapi multicast cipher selected."
					::= { wapiBasicInfo 13 }
wapiUnicastCipherRequested		OBJECT-TYPE
					SYNTAX     DisplayString
					MAX-ACCESS read-only
					STATUS     current
					DESCRIPTION
						"Wapi unicast cipher requested."
					::= { wapiBasicInfo 14 }

wapiMulticastCipherRequested		OBJECT-TYPE
					SYNTAX     DisplayString
					MAX-ACCESS read-only
					STATUS     current
					DESCRIPTION
						"Wapi multicast cipher requested."
					::= { wapiBasicInfo 15 }

--*******************************************************************************************************************************************************************
dot11RogueAPTable OBJECT-TYPE
	    SYNTAX      SEQUENCE OF Dot11RogueAPEntry
	    MAX-ACCESS  not-accessible
	    STATUS      current
	    DESCRIPTION
	        "This table shows rogue AP."
	    ::= { wtpRogue 1 }

dot11RogueAPEntry  OBJECT-TYPE
    SYNTAX      Dot11RogueAPEntry
    MAX-ACCESS  not-accessible
    STATUS      current
    DESCRIPTION
        "Rogue AP."
    INDEX { wtpMacAddr,
		rogueAPIndex }
    ::= { dot11RogueAPTable 1 }
Dot11RogueAPEntry ::=SEQUENCE{
		rogueAPIndex		INTEGER,
		rogueAPMac		DisplayString,
		rogueAPRate		INTEGER,
		rogueAPChannel		INTEGER,
		rogueAPRssi		INTEGER,
		rogueAPNoise		INTEGER,
		rogueAPBeaconInterval	INTEGER,
		rogueAPCapability	INTEGER,
		rogueAPEssid		DisplayString,
		rogueAPElemInfo		DisplayString
}

rogueAPIndex				OBJECT-TYPE
					SYNTAX     INTEGER
					MAX-ACCESS read-only
					STATUS     current
					DESCRIPTION
						"Rogue AP index"
					::= { dot11RogueAPEntry 1 }

rogueAPMac				OBJECT-TYPE
					SYNTAX     DisplayString
					MAX-ACCESS read-only
					STATUS     current
					DESCRIPTION
						"Rogue AP mac"
					::= { dot11RogueAPEntry 2 }

rogueAPRate				OBJECT-TYPE
					SYNTAX     INTEGER
					MAX-ACCESS read-only
					STATUS     current
					DESCRIPTION
						"Rogue AP rate"
					::= { dot11RogueAPEntry 3 }

rogueAPChannel				OBJECT-TYPE
					SYNTAX     INTEGER
					MAX-ACCESS read-only
					STATUS     current
					DESCRIPTION
						"Rogue AP channel"
					::= { dot11RogueAPEntry 4 }

rogueAPRssi				OBJECT-TYPE
					SYNTAX     INTEGER
					MAX-ACCESS read-only
					STATUS     current
					DESCRIPTION
						"Rogue AP rssi"
					::= { dot11RogueAPEntry 5 }

rogueAPNoise				OBJECT-TYPE
					SYNTAX     INTEGER
					MAX-ACCESS read-only
					STATUS     current
					DESCRIPTION
						"Rogue AP noise"
					::= { dot11RogueAPEntry 6 }

rogueAPBeaconInterval			OBJECT-TYPE
					SYNTAX     INTEGER
					MAX-ACCESS read-only
					STATUS     current
					DESCRIPTION
						"Rogue AP beacon interval"
					::= { dot11RogueAPEntry 7 }
rogueAPCapability			OBJECT-TYPE
					SYNTAX     INTEGER
					MAX-ACCESS read-only
					STATUS     current
					DESCRIPTION
						"Rogue AP capability"
					::= { dot11RogueAPEntry 8 }

rogueAPEssid				OBJECT-TYPE
					SYNTAX     DisplayString
					MAX-ACCESS read-only
					STATUS     current
					DESCRIPTION
						"Rogue AP essid"
					::= { dot11RogueAPEntry 9 }

rogueAPElemInfo				OBJECT-TYPE
					SYNTAX     DisplayString
					MAX-ACCESS read-only
					STATUS     current
					DESCRIPTION
						"Rogue AP element info"
					::= { dot11RogueAPEntry 10 }

--******************************************************************************************
dot11ChannelTable OBJECT-TYPE
	    SYNTAX      SEQUENCE OF Dot11ChannelEntry
	    MAX-ACCESS  not-accessible
	    STATUS      current
	    DESCRIPTION
	        "This table shows Channel monitor."
	    ::= { wtpBaseWtps 3 }

dot11ChannelEntry  OBJECT-TYPE
    SYNTAX      Dot11ChannelEntry
    MAX-ACCESS  not-accessible
    STATUS      current
    DESCRIPTION
        "Channel monitor."
    INDEX { channelID }
    ::= { dot11ChannelTable 1 }
Dot11ChannelEntry ::=SEQUENCE{
		channelID		INTEGER,
		monitorTime		TimeTicks
}
channelID				OBJECT-TYPE
					SYNTAX     INTEGER
					MAX-ACCESS read-only
					STATUS     current
					DESCRIPTION
						"Channel ID"
					::= { dot11ChannelEntry 1 }

monitorTime				OBJECT-TYPE
					SYNTAX     TimeTicks
					MAX-ACCESS read-only
					STATUS     current
					DESCRIPTION
						"Monitor time"
					::= { dot11ChannelEntry 2 }
--********************************************************************************************
--********************************************************************************************
wtpRogueSwtich		OBJECT-TYPE
			SYNTAX     INTEGER{
					enable(1),
					disable(2)
					}
			MAX-ACCESS read-write
			STATUS     current
			DESCRIPTION
				"Rogue ap switch."
			::= { wtpSwitch 1 }

wtpStatisticsSwitch	OBJECT-TYPE
			SYNTAX     INTEGER{
					enable(1),
					disable(2)
					}
			MAX-ACCESS read-write
			STATUS     current
			DESCRIPTION
				"AP statistics switch."
			::= { wtpSwitch 2 }

dot11WtpExtensionTable OBJECT-TYPE
	    SYNTAX      SEQUENCE OF Dot11WtpExtensionEntry
	    MAX-ACCESS  not-accessible
	    STATUS      current
	    DESCRIPTION
	        "Ap extension infomation switch."
	    ::= { wtpSwitch 3 }

dot11WtpExtensionEntry  OBJECT-TYPE
    SYNTAX      Dot11WtpExtensionEntry
    MAX-ACCESS  not-accessible
    STATUS      current
    DESCRIPTION
        "ap extension infomation switch."
    INDEX { wtpMacAddr }
    ::= { dot11WtpExtensionTable 1 }
Dot11WtpExtensionEntry ::=SEQUENCE{
		wtpExtensionUsed		INTEGER
}
wtpExtensionUsed			OBJECT-TYPE
					SYNTAX     INTEGER{
					enable(1),
					disable(2)
					}
					MAX-ACCESS read-write
					STATUS     current
					DESCRIPTION
						"ap extension infomation switch."
					::= { dot11WtpExtensionEntry 1 }
--********************************************************************************************
wtpFloodAttackDetectSwitch	OBJECT-TYPE
				SYNTAX     INTEGER{
					enable(1),
					disable(2)
					}
				MAX-ACCESS read-write
				STATUS     current
				DESCRIPTION
					"Flood attack detect switch."
				::= { wtpSwitch 4 }

wtpSpoofAttackDetectSwitch	OBJECT-TYPE
				SYNTAX     INTEGER{
					enable(1),
					disable(2)
					}
				MAX-ACCESS read-write
				STATUS     current
				DESCRIPTION
					"Spoof attack detect switch."
				::= { wtpSwitch 5 }

wtpWeakIVAttackDetectSwitch	OBJECT-TYPE
				SYNTAX     INTEGER{
					enable(1),
					disable(2)
					}
				MAX-ACCESS read-write
				STATUS     current
				DESCRIPTION
					"WeakIV attack detect switch."
				::= { wtpSwitch 6 }

wtpCleanAttackHistorySwitch	OBJECT-TYPE
				SYNTAX     INTEGER{
					clear(1)
					}
				MAX-ACCESS read-write
				STATUS     current
				DESCRIPTION
					"Clean attack history switch."
				::= { wtpSwitch 7 }

wtpCleanAttackStatisticalSwitch		OBJECT-TYPE
					SYNTAX     INTEGER{
							clear(1)
							}
					MAX-ACCESS read-write
					STATUS     current
					DESCRIPTION
						"Clean attack Statistical switch."
					::= { wtpSwitch 8 }

dot11WtpClearWidStatisticsTable OBJECT-TYPE
	    SYNTAX      SEQUENCE OF Dot11WtpClearWidStatisticsEntry
	    MAX-ACCESS  not-accessible
	    STATUS      current
	    DESCRIPTION
	        "Clear single wid statistics infomation switch."
	    ::= { wtpSwitch 9 }

dot11WtpClearWidStatisticsEntry  OBJECT-TYPE
    SYNTAX      Dot11WtpClearWidStatisticsEntry
    MAX-ACCESS  not-accessible
    STATUS      current
    DESCRIPTION
        "Clear single wid statistics infomation switch."
    INDEX { wtpMacAddr }
    ::= { dot11WtpClearWidStatisticsTable 1 }
Dot11WtpClearWidStatisticsEntry ::=SEQUENCE{
		wtpClearWidsStatisticalSwitch		INTEGER
}
wtpClearWidsStatisticalSwitch		OBJECT-TYPE
					SYNTAX     INTEGER{
							clear(1)
							}
					MAX-ACCESS read-write
					STATUS     current
					DESCRIPTION
						"Clear single ap wids statistics information ."
					::= { dot11WtpClearWidStatisticsEntry 1 }
--********************************************************************************************
FloodAttackTimes			OBJECT-TYPE
					SYNTAX     Counter32
					MAX-ACCESS read-only
					STATUS     current
					DESCRIPTION
						"Flooding attack times."
					::= { widStatistics 1 }

SpoofingAttackTimes			OBJECT-TYPE
					SYNTAX     Counter32
					MAX-ACCESS read-only
					STATUS     current
					DESCRIPTION
						"Spoofing attack times."
					::= { widStatistics 2 }

WeakIVAttackTimes			OBJECT-TYPE
					SYNTAX     Counter32
					MAX-ACCESS read-only
					STATUS     current
					DESCRIPTION
						"WeakIV attack times."
					::= { widStatistics 3 }

dot11WtpWidStatisticsTable OBJECT-TYPE
	    SYNTAX      SEQUENCE OF Dot11WtpWidStatisticsEntry
	    MAX-ACCESS  not-accessible
	    STATUS      current
	    DESCRIPTION
	        "Ap wid statistics infomation switch."
	    ::= { widStatistics 4 }

dot11WtpWidStatisticsEntry  OBJECT-TYPE
    SYNTAX      Dot11WtpWidStatisticsEntry
    MAX-ACCESS  not-accessible
    STATUS      current
    DESCRIPTION
        "ap wid statistics infomation switch."
    INDEX { wtpMacAddr }
    ::= { dot11WtpWidStatisticsTable 1 }
Dot11WtpWidStatisticsEntry ::=SEQUENCE{
		wtpFloodAttackTimes		Counter32,
		wtpSpoofingAttackTimes		Counter32,
		wtpWeakIVAttackTimes		Counter32
}
wtpFloodAttackTimes			OBJECT-TYPE
					SYNTAX     Counter32
					MAX-ACCESS read-only
					STATUS     current
					DESCRIPTION
						"Flooding attack times."
					::= { dot11WtpWidStatisticsEntry 1 }

wtpSpoofingAttackTimes			OBJECT-TYPE
					SYNTAX     Counter32
					MAX-ACCESS read-only
					STATUS     current
					DESCRIPTION
						"Spoofing attack times."
					::= { dot11WtpWidStatisticsEntry 2 }

wtpWeakIVAttackTimes			OBJECT-TYPE
					SYNTAX     Counter32
					MAX-ACCESS read-only
					STATUS     current
					DESCRIPTION
						"WeakIV attack times."
					::= { dot11WtpWidStatisticsEntry 3 }
--*******************************************************************************************
dot11WidDetectHistoryTable OBJECT-TYPE
	    SYNTAX      SEQUENCE OF Dot11WidDetectHistoryEntry
	    MAX-ACCESS  not-accessible
	    STATUS      current
	    DESCRIPTION
	        "Ap wid statistics infomation switch."
	    ::= { widStatistics 5 }

dot11WidDetectHistoryEntry  OBJECT-TYPE
    SYNTAX      Dot11WidDetectHistoryEntry
    MAX-ACCESS  not-accessible
    STATUS      current
    DESCRIPTION
        "ap wid statistics infomation switch."
    INDEX { deviceID }
    ::= { dot11WidDetectHistoryTable 1 }
Dot11WidDetectHistoryEntry ::=SEQUENCE{
		deviceID		INTEGER,
		deviceMac		DisplayString,
		attackType		DisplayString,
		frameType		DisplayString,
		attackCount		Counter32,
		firstAttack		DisplayString,
		lastAttack		DisplayString,
		RogStaMonApNum		Integer32,
		RogStaAccBSSID		DisplayString,
		RogStaMaxSigStrength	Integer32,
		RogStaChannel		INTEGER,
		RogStaAdHocStatus	TruthValue,
		RogStaAttackStatus	TruthValue,
		RogStaToIgnore		TruthValue		
}
deviceID				OBJECT-TYPE
					SYNTAX     INTEGER
					MAX-ACCESS read-only
					STATUS     current
					DESCRIPTION
						"ID."
					::= { dot11WidDetectHistoryEntry 1 }

deviceMac				OBJECT-TYPE
					SYNTAX     DisplayString
					MAX-ACCESS read-only
					STATUS     current
					DESCRIPTION
						"Device mac."
					::= { dot11WidDetectHistoryEntry 2 }

attackType				OBJECT-TYPE
					SYNTAX     DisplayString
					MAX-ACCESS read-only
					STATUS     current
					DESCRIPTION
						"Attack type."
					::= { dot11WidDetectHistoryEntry 3 }

frameType				OBJECT-TYPE
					SYNTAX     DisplayString
					MAX-ACCESS read-only
					STATUS     current
					DESCRIPTION
						"Frame type."
					::= { dot11WidDetectHistoryEntry 4 }

attackCount				OBJECT-TYPE
					SYNTAX     Counter32
					MAX-ACCESS read-only
					STATUS     current
					DESCRIPTION
						"Attack count."
					::= { dot11WidDetectHistoryEntry 5 }

firstAttack				OBJECT-TYPE
					SYNTAX     DisplayString
					MAX-ACCESS read-only
					STATUS     current
					DESCRIPTION
						"First attack time."
					::= { dot11WidDetectHistoryEntry 6 }

lastAttack				OBJECT-TYPE
					SYNTAX     DisplayString
					MAX-ACCESS read-only
					STATUS     current
					DESCRIPTION
						"Last attack time."
					::= { dot11WidDetectHistoryEntry 7 }
					
RogStaMonApNum				OBJECT-TYPE
					SYNTAX      	Integer32
					MAX-ACCESS  	read-only
					STATUS      	current
					DESCRIPTION
				      		"The monitor AP number that detect rogue station."
					::= { dot11WidDetectHistoryEntry 8 }	
					
RogStaAccBSSID				OBJECT-TYPE
					SYNTAX      	DisplayString
					MAX-ACCESS  	read-only
					STATUS      	current
					DESCRIPTION
					      "The rogue station access BSSID."
					::= { dot11WidDetectHistoryEntry 9 }									
					
RogStaMaxSigStrength			OBJECT-TYPE
					SYNTAX      	Integer32
					MAX-ACCESS  	read-only
					STATUS      	current
					DESCRIPTION
					      "WIDS receive from the suspect the maximum station signal strength."
					::= { dot11WidDetectHistoryEntry 10 }		
					
RogStaChannel				OBJECT-TYPE
					SYNTAX      	INTEGER
					MAX-ACCESS  	read-only
					STATUS      	current
					DESCRIPTION
					      "Rogue station channel."
					::= { dot11WidDetectHistoryEntry 11 }	
					
RogStaAdHocStatus			OBJECT-TYPE
					SYNTAX      	TruthValue
					MAX-ACCESS  	read-only
					STATUS      	current
					DESCRIPTION
					      "Rogue station whether works in Ad-Hoc mode."
					::= { dot11WidDetectHistoryEntry 12 }

RogStaAttackStatus			OBJECT-TYPE
					SYNTAX      	TruthValue
					MAX-ACCESS  	read-write
					STATUS      	current
					DESCRIPTION
					      "Whether strategies to the rogue station."
					::= { dot11WidDetectHistoryEntry 13 }

RogStaToIgnore				OBJECT-TYPE
					SYNTAX      	TruthValue
					MAX-ACCESS  	read-write
					STATUS      	current
					DESCRIPTION
					      "Whether or not ignore the rogue Station."
					::= { dot11WidDetectHistoryEntry 14 }	
--********************************************************************************************
dot11WtpBssIDNumTable OBJECT-TYPE
	    SYNTAX      SEQUENCE OF Dot11WtpBssIDNumEntry
	    MAX-ACCESS  not-accessible
	    STATUS      current
	    DESCRIPTION
	        "Ap wid statistics infomation switch."
	    ::= { wtpIDIndex 1 }

dot11WtpBssIDNumEntry  OBJECT-TYPE
    SYNTAX      Dot11WtpBssIDNumEntry
    MAX-ACCESS  not-accessible
    STATUS      current
    DESCRIPTION
        "Wtp Total BssIDnum."
    INDEX { wtpID }
    ::= { dot11WtpBssIDNumTable 1 }
Dot11WtpBssIDNumEntry ::=SEQUENCE{
		wtpID			INTEGER,
		BssIDTatolNum		Counter32

}
wtpID			                OBJECT-TYPE
					SYNTAX     INTEGER
					MAX-ACCESS read-only
					STATUS     current
					DESCRIPTION
						"wtpID."
					::= { dot11WtpBssIDNumEntry 1 }

BssIDTatolNum			        OBJECT-TYPE
					SYNTAX     Counter32
					MAX-ACCESS read-only
					STATUS     current
					DESCRIPTION
						"BssIDTatolNum."
					::= { dot11WtpBssIDNumEntry 2 }
--*******************************************************************************************************************************************************************
dot11WlanDataPktsTable 	OBJECT-TYPE
				SYNTAX	SEQUENCE OF Dot11WlanDataPktsEntry
				MAX-ACCESS not-accessible
				STATUS		current
				DESCRIPTION
					"The table listing the dot11 wlan data packets information."
				::={ wlanData 1 }

dot11WlanDataPktsEntry		OBJECT-TYPE
				SYNTAX	Dot11WlanDataPktsEntry
				MAX-ACCESS not-accessible
				STATUS	current
				DESCRIPTION
					"An entry (conceptual row) in the dot11WlanDataPktsTable."
				INDEX	{ wlanCurrID }
				::={ dot11WlanDataPktsTable 1 }
Dot11WlanDataPktsEntry ::=SEQUENCE {
	ethernetRecvCorrectFrames	        Counter32,
	ethernetRecvCorrectBytes		Counter64,
	ethernetSendCorrectBytes		Counter64
}
ethernetRecvCorrectFrames		OBJECT-TYPE
					SYNTAX     Counter32
					MAX-ACCESS read-only
					STATUS     current
					DESCRIPTION
				        	"The total bytes which received from terminal(Appointed SSID)."
					::= { dot11WlanDataPktsEntry 1 }

ethernetRecvCorrectBytes		OBJECT-TYPE
					SYNTAX     Counter64
					MAX-ACCESS read-only
					STATUS     current
					DESCRIPTION
				        	"The total packages which received from terminal(Appointed SSID).(bts)"
					::= { dot11WlanDataPktsEntry 2 }

ethernetSendCorrectBytes		OBJECT-TYPE
					SYNTAX     Counter64
					MAX-ACCESS read-only
					STATUS     current
					DESCRIPTION
				        	"The total bytes which received from terminal(Appointed SSID).(bts)"
					::= { dot11WlanDataPktsEntry 3 }


dot11WlanRadioDataTable 	OBJECT-TYPE
				SYNTAX	SEQUENCE OF Dot11WlanRadioDataEntry
				MAX-ACCESS not-accessible
				STATUS		current
				DESCRIPTION
					"The table listing the dot11 wlan data packets information."
				::={ wlanData 2 }

dot11WlanRadioDataEntry		OBJECT-TYPE
				SYNTAX	Dot11WlanRadioDataEntry
				MAX-ACCESS not-accessible
				STATUS	current
				DESCRIPTION
					"An entry (conceptual row) in the dot11WlanRadioDataTable."
				INDEX	{ wlanCurrID }
				::={ dot11WlanRadioDataTable 1 }

Dot11WlanRadioDataEntry ::=SEQUENCE {
	WlanradioRecvFlow	        Counter64,
	WlanradioSendFlow		Counter64,
        WlanradioReSendFrames           Counter64,
        WlanradioSendDiscardFrames      Counter64,
        WlanradioSendErrFrames          Counter64,
        WlanradioRecvDiscardFrames      Counter64,
        WlanradioReRecvFrames           Counter64,
        WlanradioRecvSpeed	        Integer32,
	WlanradioSendSpeed		Integer32
}
WlanradioRecvFlow		        OBJECT-TYPE
					SYNTAX     Counter64
					MAX-ACCESS read-only
					STATUS     current
					DESCRIPTION
				        	"The Wireless radioRecvFlow which received from terminal(Appointed SSID)."
					::= { dot11WlanRadioDataEntry 1 }

WlanradioSendFlow		                OBJECT-TYPE
					SYNTAX     Counter64
					MAX-ACCESS read-only
					STATUS     current
					DESCRIPTION
				        	"The Wireless radioSendFlow which received from terminal(Appointed SSID).(bts)"
					::= { dot11WlanRadioDataEntry 2 }

WlanradioReSendFrames		        OBJECT-TYPE
					SYNTAX     Counter64
					MAX-ACCESS read-only
					STATUS     current
					DESCRIPTION
				        	"The Wireless radioReSendFrames which received from terminal(Appointed SSID).(bts)"
					::= { dot11WlanRadioDataEntry 3 }

WlanradioSendDiscardFrames		                OBJECT-TYPE
					SYNTAX     Counter64
					MAX-ACCESS read-only
					STATUS     current
					DESCRIPTION
				        	"The Wireless radioSendDiscardFrames which received from terminal(Appointed SSID).(bts)"
					::= { dot11WlanRadioDataEntry 4 }

WlanradioSendErrFrames		        OBJECT-TYPE
					SYNTAX     Counter64
					MAX-ACCESS read-only
					STATUS     current
					DESCRIPTION
				        	"The Wireless radioSendErrFrames which received from terminal(Appointed SSID).(bts)"
					::= { dot11WlanRadioDataEntry 5 }

WlanradioRecvDiscardFrames		OBJECT-TYPE
					SYNTAX     Counter64
					MAX-ACCESS read-only
					STATUS     current
					DESCRIPTION
				        	"The Wireless radioRecvDiscardFrames which received from terminal(Appointed SSID).(bts)"
					::= { dot11WlanRadioDataEntry 6 }
WlanradioReRecvFrames		        OBJECT-TYPE
					SYNTAX     Counter64
					MAX-ACCESS read-only
					STATUS     current
					DESCRIPTION
				        	"The Wireless radioReRecvFrames which received from terminal(Appointed SSID).(bts)"
					::= { dot11WlanRadioDataEntry 7 }

WlanradioRecvSpeed		        OBJECT-TYPE
					SYNTAX     Integer32
					MAX-ACCESS read-only
					STATUS     current
					DESCRIPTION
				        	"The Wireless radioRecvSpeed which received from terminal(Appointed SSID)."
					::= { dot11WlanRadioDataEntry 8 }

WlanradioSendSpeed		                OBJECT-TYPE
					SYNTAX     Integer32
					MAX-ACCESS read-only
					STATUS     current
					DESCRIPTION
				        	"The Wireless radioSendSpeed which received from terminal(Appointed SSID).(bts)"
					::= { dot11WlanRadioDataEntry 9 }



					
--*******************************************************************************************************************************************************************
dot11WtpTeminalTable    	OBJECT-TYPE
				SYNTAX	SEQUENCE OF Dot11WtpTeminalEntry
				MAX-ACCESS not-accessible
				STATUS		current
				DESCRIPTION
					"The table listing the dot11 wtp teminal infos."
				::={ wlanPortal 1 }

dot11WtpTeminalEntry		OBJECT-TYPE
				SYNTAX	Dot11WtpTeminalEntry
				MAX-ACCESS not-accessible
				STATUS	current
				DESCRIPTION
					"An entry (conceptual row) in the dot11WtpTeminalTable."
				INDEX	{ wtpMacAddr }				
				::={ dot11WtpTeminalTable 1 }
				
Dot11WtpTeminalEntry ::=SEQUENCE {        
	portalCurusernum    	        Counter32,
	portalErrLogoffnum		Counter32,
	portalReqnum			Counter32,
	portalReqsuccnum		Counter32,
	portalReqfailnum 		Counter32,
	portalAllUserOnlineTime	    TimeTicks,
	macAuthCurusernum    	    Counter32,
	macAuthErrLogoffnum			Counter32,
	macAuthReqnum				Counter32,
	macAuthReqsuccnum			Counter32,
	macAuthReqfailnum 			Counter32,
	macAuthAllUserOnlineTime	TimeTicks	
}
portalCurusernum			OBJECT-TYPE
					SYNTAX     Counter32
					MAX-ACCESS read-only
					STATUS     current
					DESCRIPTION
				        	"The ap portal current user total number)."
					::= { dot11WtpTeminalEntry 1 }

portalErrLogoffnum			OBJECT-TYPE
					SYNTAX     Counter32
					MAX-ACCESS read-only
					STATUS     current
					DESCRIPTION
				        	"The ap portal fail number."
					::= { dot11WtpTeminalEntry 2 }					
					
portalReqnum				OBJECT-TYPE
					SYNTAX     Counter32
					MAX-ACCESS read-only
					STATUS     current
					DESCRIPTION
				        	"The ap portal request number."
					::= { dot11WtpTeminalEntry 3 }
										
portalReqsuccnum			OBJECT-TYPE
					SYNTAX     Counter32
					MAX-ACCESS read-only
					STATUS     current
					DESCRIPTION
				        	"The ap portal request success number."
					::= { dot11WtpTeminalEntry 4 }					

portalReqfailnum			OBJECT-TYPE
					SYNTAX     Counter32
					MAX-ACCESS read-only
					STATUS     current
					DESCRIPTION
				        	"The ap portal request fail number."
					::= { dot11WtpTeminalEntry 5 }

portalAllUserOnlineTime			OBJECT-TYPE
					SYNTAX     TimeTicks
					MAX-ACCESS read-only
					STATUS     current
					DESCRIPTION
				        	"The  portal all users online time."
					::= { dot11WtpTeminalEntry 6 }

macAuthCurusernum			OBJECT-TYPE
					SYNTAX     Counter32
					MAX-ACCESS read-only
					STATUS     current
					DESCRIPTION
				        	"The ap mac auth current user total number)."
					::= { dot11WtpTeminalEntry 7 }

macAuthErrLogoffnum			OBJECT-TYPE
					SYNTAX     Counter32
					MAX-ACCESS read-only
					STATUS     current
					DESCRIPTION
				        	"The ap mac auth fail number."
					::= { dot11WtpTeminalEntry 8 }					
					
macAuthReqnum				OBJECT-TYPE
					SYNTAX     Counter32
					MAX-ACCESS read-only
					STATUS     current
					DESCRIPTION
				        	"The ap mac auth request number."
					::= { dot11WtpTeminalEntry 9 }
										
macAuthReqsuccnum			OBJECT-TYPE
					SYNTAX     Counter32
					MAX-ACCESS read-only
					STATUS     current
					DESCRIPTION
				        	"The ap mac auth request success number."
					::= { dot11WtpTeminalEntry 10 }					

macAuthReqfailnum			OBJECT-TYPE
					SYNTAX     Counter32
					MAX-ACCESS read-only
					STATUS     current
					DESCRIPTION
				        	"The ap mac auth request fail number."
					::= { dot11WtpTeminalEntry 11 }

macAuthAllUserOnlineTime			OBJECT-TYPE
					SYNTAX     TimeTicks
					MAX-ACCESS read-only
					STATUS     current
					DESCRIPTION
				        	"The mac auth all users online time."
					::= { dot11WtpTeminalEntry 12 }

dot11PortalUserInfoTable 	OBJECT-TYPE
				SYNTAX	SEQUENCE OF Dot11PortalUserInfoEntry
				MAX-ACCESS not-accessible
				STATUS		current
				DESCRIPTION
					"The table listing the dot11 portal user info."
				::={ wlanPortal 2 }

dot11PortalUserInfoEntry	OBJECT-TYPE
				SYNTAX	Dot11PortalUserInfoEntry
				MAX-ACCESS not-accessible
				STATUS	current
				DESCRIPTION
					"An entry (conceptual row) in the dot11PortalUserInfoEntry."
				INDEX	{ wtpMacAddr,
					  wtpStaMacAddr }
				::={ dot11PortalUserInfoTable 1 }

Dot11PortalUserInfoEntry ::=SEQUENCE {	
	portalUserip			 IpAddress,
	portalUsername                   DisplayString,
	portalUserUptime                 DisplayString,
	portalUseronline         	 TimeTicks,
	userAuthType			 INTEGER,
	portalUseripv6address		InetAddressIPv6
}

portalUserip				OBJECT-TYPE
					SYNTAX     IpAddress
					MAX-ACCESS read-only
					STATUS     current
					DESCRIPTION
				        	"The  portal user ip address."
					::= { dot11PortalUserInfoEntry 1 }	
										
portalUsername				OBJECT-TYPE
					SYNTAX     DisplayString
					MAX-ACCESS read-only
					STATUS     current
					DESCRIPTION
				        	"The  portal user name."
					::= { dot11PortalUserInfoEntry 2 }	
					
portalUserUptime			OBJECT-TYPE
					SYNTAX     DisplayString
					MAX-ACCESS read-only
					STATUS     current
					DESCRIPTION
				        	"The  portal user login time."
					::= { dot11PortalUserInfoEntry 3 }	
					
portalUseronline			OBJECT-TYPE
					SYNTAX     TimeTicks
					MAX-ACCESS read-only
					STATUS     current
					DESCRIPTION
				        	"The  portal user online time."
					::= { dot11PortalUserInfoEntry 4 }																			
					
userAuthType				OBJECT-TYPE
					SYNTAX     INTEGER{
								portalAuth(1),
								authFree(2),
								associateAuth(3),
								autoAuth(4)
							}
					MAX-ACCESS read-only
					STATUS     current
					DESCRIPTION
				        	"The user auth typ."
					::= { dot11PortalUserInfoEntry 5 }

portalUseripv6address			OBJECT-TYPE
					SYNTAX     InetAddressIPv6
					MAX-ACCESS read-only
					STATUS     current
					DESCRIPTION
				        	"The portal User ipv6address ."
					::= { dot11PortalUserInfoEntry 7 }																			

dot11WtpBssidTeminalTable    	OBJECT-TYPE
				SYNTAX	SEQUENCE OF Dot11WtpBssidTeminalEntry
				MAX-ACCESS not-accessible
				STATUS		current
				DESCRIPTION
					"The table listing the dot11 wtp teminal infos."
				::={ wlanPortal 3 }


dot11WtpBssidTeminalEntry		OBJECT-TYPE
				SYNTAX	Dot11WtpBssidTeminalEntry
				MAX-ACCESS not-accessible
				STATUS	current
				DESCRIPTION
					"An entry (conceptual row) in the dot11WtpTeminalTable."
				INDEX	{ wtpMacAddr ,
					wtpWirelessIfIndex ,
					wlanCurrID
				}				
				::={ dot11WtpBssidTeminalTable 1 }
				
Dot11WtpBssidTeminalEntry ::=SEQUENCE {        
	pBssidCurusernum    	        Counter32,
	pBssidLogoffnum			Counter32,
	pBssidReqnum			Counter32,
	pBssidReqsuccnum		Counter32,
	pBssidReqfailnum 		Counter32,
	pBssidReqSuccRate		INTEGER,
	pBssidUserRedirReqNum		Counter32,
	pBssidUserRedirReqSuccNum	Counter32,
	pBssidUserRedirReqSuccRate	INTEGER,
	pBssidRadiusAuthReqNum		Counter32,
	pBssidRadiusAuthReqSuccNum	Counter32,
	pBssidRadiusAuthReqSuccRate	INTEGER,
	pBssidChallengeReqNum		Counter32,
	pBssidChallengeReqSuccNum	Counter32,
	pBssidChallengeReqSuccRate	INTEGER
}
pBssidCurusernum			OBJECT-TYPE
					SYNTAX     Counter32
					MAX-ACCESS read-only
					STATUS     current
					DESCRIPTION
				        	"The ap depend on portal current user total number."
					::= { dot11WtpBssidTeminalEntry 1 }

pBssidLogoffnum				OBJECT-TYPE
					SYNTAX     Counter32
					MAX-ACCESS read-only
					STATUS     current
					DESCRIPTION
				        	"The ap depend on portal fail number."
					::= { dot11WtpBssidTeminalEntry 2 }					
					
pBssidReqnum				OBJECT-TYPE
					SYNTAX     Counter32
					MAX-ACCESS read-only
					STATUS     current
					DESCRIPTION
				        	"The ap depend on portal request number."
					::= { dot11WtpBssidTeminalEntry 3 }
										
pBssidReqsuccnum			OBJECT-TYPE
					SYNTAX     Counter32
					MAX-ACCESS read-only
					STATUS     current
					DESCRIPTION
				        	"The ap depend on portal request success number."
					::= { dot11WtpBssidTeminalEntry 4 }					

pBssidReqfailnum			OBJECT-TYPE
					SYNTAX     Counter32
					MAX-ACCESS read-only
					STATUS     current
					DESCRIPTION
				        	"The ap depend on bssid portal request fail number."
					::= { dot11WtpBssidTeminalEntry 5 }																		

pBssidReqSuccRate			OBJECT-TYPE
					SYNTAX     INTEGER
					MAX-ACCESS read-only
					STATUS     current
					DESCRIPTION
				        	"The ap depend on bssid portal request success rate."
					::= { dot11WtpBssidTeminalEntry 6 }
					
pBssidUserRedirReqNum			OBJECT-TYPE
					SYNTAX     Counter32
					MAX-ACCESS read-only
					STATUS     current
					DESCRIPTION
				        	"The ap depend on bssid portal page request number."
					::= { dot11WtpBssidTeminalEntry 7 }	
					
pBssidUserRedirReqSuccNum		OBJECT-TYPE
					SYNTAX     Counter32
					MAX-ACCESS read-only
					STATUS     current
					DESCRIPTION
				        	"The ap depend on bssid portal page request success number."
					::= { dot11WtpBssidTeminalEntry 8 }										
					
pBssidUserRedirReqSuccRate		OBJECT-TYPE
					SYNTAX     INTEGER
					MAX-ACCESS read-only
					STATUS     current
					DESCRIPTION
				        	"The ap depend on bssid portal page request success rate."
					::= { dot11WtpBssidTeminalEntry 9 }	
					
pBssidRadiusAuthReqNum			OBJECT-TYPE
					SYNTAX     Counter32
					MAX-ACCESS read-only
					STATUS     current
					DESCRIPTION
				        	"The ap depend on bssid radius authentication request number."
					::= { dot11WtpBssidTeminalEntry 10 }		
					
pBssidRadiusAuthReqSuccNum		OBJECT-TYPE
					SYNTAX     Counter32
					MAX-ACCESS read-only
					STATUS     current
					DESCRIPTION
				        	"The ap depend on bssid radius authentication request success number."
					::= { dot11WtpBssidTeminalEntry 11 }														

pBssidRadiusAuthReqSuccRate		OBJECT-TYPE
					SYNTAX     INTEGER
					MAX-ACCESS read-only
					STATUS     current
					DESCRIPTION
				        	"The ap depend on bssid radius authentication request success rate."
					::= { dot11WtpBssidTeminalEntry 12 }	
					
pBssidChallengeReqNum			OBJECT-TYPE
					SYNTAX     Counter32
					MAX-ACCESS read-only
					STATUS     current
					DESCRIPTION
				        	"The ap depend on bssid challenge request number."
					::= { dot11WtpBssidTeminalEntry 13 }		
					
pBssidChallengeReqSuccNum		OBJECT-TYPE
					SYNTAX     Counter32
					MAX-ACCESS read-only
					STATUS     current
					DESCRIPTION
				        	"The ap depend on bssid challenge request success number."
					::= { dot11WtpBssidTeminalEntry 14 }	
					
pBssidChallengeReqSuccRate		OBJECT-TYPE
					SYNTAX     INTEGER
					MAX-ACCESS read-only
					STATUS     current
					DESCRIPTION
				        	"The ap depend on bssid challenge request success rate."
					::= { dot11WtpBssidTeminalEntry 15 }												



dot11WtpIfTeminalTable    	OBJECT-TYPE
				SYNTAX	SEQUENCE OF Dot11WtpIfTeminalEntry
				MAX-ACCESS not-accessible
				STATUS		current
				DESCRIPTION
					"The table listing the dot11 wtp teminal infos."
				::={ wlanPortal 4 }


dot11WtpIfTeminalEntry		OBJECT-TYPE
				SYNTAX	Dot11WtpIfTeminalEntry
				MAX-ACCESS not-accessible
				STATUS	current
				DESCRIPTION
					"An entry (conceptual row) in the dot11WtpIfTeminalTable."
				INDEX	{ wtpMacAddr ,
					wtpWirelessIfIndex 
				}				
				::={ dot11WtpIfTeminalTable 1 }
				
Dot11WtpIfTeminalEntry ::=SEQUENCE {        
	pIfCurusernum    	        Counter32,
	pIfLogoffnum			Counter32,
	pIfReqnum			Counter32,
	pIfReqsuccnum			Counter32,
	pIfReqfailnum 			Counter32	
}
pIfCurusernum				OBJECT-TYPE
					SYNTAX     Counter32
					MAX-ACCESS read-only
					STATUS     current
					DESCRIPTION
				        	"The ap depend on portal current user total number."
					::= { dot11WtpIfTeminalEntry 1 }

pIfLogoffnum				OBJECT-TYPE
					SYNTAX     Counter32
					MAX-ACCESS read-only
					STATUS     current
					DESCRIPTION
				        	"The ap depend on portal fail number."
					::= { dot11WtpIfTeminalEntry 2 }					
					
pIfReqnum				OBJECT-TYPE
					SYNTAX     Counter32
					MAX-ACCESS read-only
					STATUS     current
					DESCRIPTION
				        	"The ap depend on portal request number."
					::= { dot11WtpIfTeminalEntry 3 }
										
pIfReqsuccnum				OBJECT-TYPE
					SYNTAX     Counter32
					MAX-ACCESS read-only
					STATUS     current
					DESCRIPTION
				        	"The ap depend on portal request success number."
					::= { dot11WtpIfTeminalEntry 4 }					

pIfReqfailnum				OBJECT-TYPE
					SYNTAX     Counter32
					MAX-ACCESS read-only
					STATUS     current
					DESCRIPTION
				        	"The ap depend on bssid portal request fail number."
					::= { dot11WtpIfTeminalEntry 5 }

dot11WtpWirelessAuthTable    	OBJECT-TYPE
				SYNTAX	SEQUENCE OF Dot11WtpWirelessAuthEntry
				MAX-ACCESS not-accessible
				STATUS		current
				DESCRIPTION
					"The table listing the dot11 wtp wireless auth infos."
				::={ wlanPortal 5 }

dot11WtpWirelessAuthEntry		OBJECT-TYPE
				SYNTAX	Dot11WtpWirelessAuthEntry
				MAX-ACCESS not-accessible
				STATUS	current
				DESCRIPTION
					"An entry in the dot11WtpWirelessAuthTable."
				INDEX	{ wtpMacAddr }				
				::={ dot11WtpWirelessAuthTable 1 }

Dot11WtpWirelessAuthEntry ::=SEQUENCE {        
	authFreeCurusernum    	    Counter32,
	authFreeErrLogoffnum		Counter32,
	authFreeAllUserOnlineTime	TimeTicks,
	assocAuthCurusernum    	Counter32,
	assocAuthErrLogoffnum		Counter32,
	assocAuthReqnum				Counter32,
	assocAuthReqsuccnum			Counter32,
	assocAuthReqfailnum 		Counter32,
	assocAuthAllUserOnlineTime	TimeTicks,	
	assocAuthOnlineUsernum                  INTEGER,
	allAssociateAuthUserOnlineTime         TimeTicks,
	assocAuthUserLostConnectionCnt         Counter32,
	autoAuthOnlineUsernum	               INTEGER,
	allAutoAuthUserOnlineTime              TimeTicks,
	autoAuthUserLostConnectionCnt          Counter32,
	autoAuthReqCnt                         Counter32,
	autoAuthSucCnt                         Counter32,
	autoAuthReqFailCnt                     Counter32
}
authFreeCurusernum			OBJECT-TYPE
					SYNTAX     Counter32
					MAX-ACCESS read-only
					STATUS     current
					DESCRIPTION
				        	"The ap auth free current user total number)."
					::= { dot11WtpWirelessAuthEntry 1 }

authFreeErrLogoffnum		   OBJECT-TYPE
					SYNTAX     Counter32
					MAX-ACCESS read-only
					STATUS     current
					DESCRIPTION
				        	"The ap auth free fail number."
					::= { dot11WtpWirelessAuthEntry 2 }					

authFreeAllUserOnlineTime	   OBJECT-TYPE
					SYNTAX     TimeTicks
					MAX-ACCESS read-only
					STATUS     current
					DESCRIPTION
				        	"The auth free all users online time."
					::= { dot11WtpWirelessAuthEntry 3 }

assocAuthCurusernum			OBJECT-TYPE
					SYNTAX     Counter32
					MAX-ACCESS read-only
					STATUS     current
					DESCRIPTION
				        	"The ap assoc auth current user total number)."
					::= { dot11WtpWirelessAuthEntry 4 }

assocAuthErrLogoffnum			OBJECT-TYPE
					SYNTAX     Counter32
					MAX-ACCESS read-only
					STATUS     current
					DESCRIPTION
				        	"The ap assoc auth fail number."
					::= { dot11WtpWirelessAuthEntry 5 }					
					
assocAuthReqnum				OBJECT-TYPE
					SYNTAX     Counter32
					MAX-ACCESS read-only
					STATUS     current
					DESCRIPTION
				        	"The ap assoc auth request number."
					::= { dot11WtpWirelessAuthEntry 6 }
										
assocAuthReqsuccnum			OBJECT-TYPE
					SYNTAX     Counter32
					MAX-ACCESS read-only
					STATUS     current
					DESCRIPTION
				        	"The ap assoc auth request success number."
					::= { dot11WtpWirelessAuthEntry 7 }					

assocAuthReqfailnum			OBJECT-TYPE
					SYNTAX     Counter32
					MAX-ACCESS read-only
					STATUS     current
					DESCRIPTION
				        	"The ap assoc auth request fail number."
					::= { dot11WtpWirelessAuthEntry 8 }

assocAuthAllUserOnlineTime			OBJECT-TYPE
					SYNTAX     TimeTicks
					MAX-ACCESS read-only
					STATUS     current
					DESCRIPTION
				        	"The assoc auth all users online time."
					::= { dot11WtpWirelessAuthEntry 9 }
assocAuthOnlineUsernum			OBJECT-TYPE
					SYNTAX     INTEGER
					MAX-ACCESS read-only
					STATUS     current
					DESCRIPTION
				        "The WEP/PSK current user total number of AP"
					::= { dot11WtpWirelessAuthEntry 10 }
allAssociateAuthUserOnlineTime			OBJECT-TYPE
					SYNTAX     TimeTicks
					MAX-ACCESS read-only
					STATUS     current
					DESCRIPTION
				        	"The WEP/PSK all users online time of AP."
					::= { dot11WtpWirelessAuthEntry 11}
assocAuthUserLostConnectionCnt			OBJECT-TYPE
					SYNTAX     Counter32
					MAX-ACCESS read-only
					STATUS     current
					DESCRIPTION
				        	"The WEP/PSK certification fail number of AP."
					::= { dot11WtpWirelessAuthEntry 12 }
autoAuthOnlineUsernum			OBJECT-TYPE
					SYNTAX     INTEGER
					MAX-ACCESS read-only
					STATUS     current
					DESCRIPTION
				        "The SIM/PEAP current user total number of AP."
					::= { dot11WtpWirelessAuthEntry 13 }
allAutoAuthUserOnlineTime			OBJECT-TYPE
					SYNTAX     TimeTicks
					MAX-ACCESS read-only
					STATUS     current
					DESCRIPTION
					     "The SIM/PEAP all users online time of AP."
					::= { dot11WtpWirelessAuthEntry 14 }
autoAuthUserLostConnectionCnt			OBJECT-TYPE
					SYNTAX     Counter32
					MAX-ACCESS read-only
					STATUS     current
					DESCRIPTION
				        	" The SIM/PEAP fail number of AP."
					::= { dot11WtpWirelessAuthEntry 15 }
autoAuthReqCnt			OBJECT-TYPE
					SYNTAX     Counter32
					MAX-ACCESS read-only
					STATUS     current
					DESCRIPTION
				        	" The SIM/PEAP request number of AP."
					::= { dot11WtpWirelessAuthEntry 16 }
autoAuthSucCnt			OBJECT-TYPE
					SYNTAX     Counter32
					MAX-ACCESS read-only
					STATUS     current
					DESCRIPTION
				        	" The SIM/PEAP request success number of AP."
					::= { dot11WtpWirelessAuthEntry 17 }
autoAuthReqFailCnt			OBJECT-TYPE
					SYNTAX     Counter32
					MAX-ACCESS read-only
					STATUS     current
					DESCRIPTION
				        	" The SIM/PEAP request fail number of AP."
					::= { dot11WtpWirelessAuthEntry 18 }

--*******************************************************************************************************************************************************************
dot11SsidTeminalTable    	OBJECT-TYPE
				SYNTAX	SEQUENCE OF Dot11SsidTeminalEntry
				MAX-ACCESS not-accessible
				STATUS		current
				DESCRIPTION
					"The table listing the dot11 ssid teminal infos."
				::={ wlanPortal 6 }


dot11SsidTeminalEntry	OBJECT-TYPE
				SYNTAX	Dot11SsidTeminalEntry
				MAX-ACCESS not-accessible
				STATUS	current
				DESCRIPTION
					"An entry (conceptual row) in the dot11SsidTeminalTable."
				INDEX	{ 
					wlanCurrID
				}				
				::={ dot11SsidTeminalTable 1 }
				
Dot11SsidTeminalEntry ::=SEQUENCE {	
	pSsidUserRedirReqNum		Counter32,
	pSsidUserRedirReqSuccNum	Counter32,
	pSsidUserRedirReqSuccRate	INTEGER,
	pSsidRadiusAuthReqNum		Counter32,
	pSsidRadiusAuthReqSuccNum	Counter32,
	pSsidRadiusAuthReqSuccRate	INTEGER,
	pSsidChallengeReqNum		Counter32,
	pSsidChallengeReqSuccNum	Counter32,
	pSsidChallengeReqSuccRate	INTEGER,
	pSsidReqnum			Counter32,
	pSsidReqsuccnum			Counter32,
	pSsidReqSuccRate		INTEGER
}										
pSsidUserRedirReqNum			OBJECT-TYPE
					SYNTAX     Counter32
					MAX-ACCESS read-only
					STATUS     current
					DESCRIPTION
				        	"The number of portal page request number based on the SSID."
					::= { dot11SsidTeminalEntry 1 }	
					
pSsidUserRedirReqSuccNum		OBJECT-TYPE
					SYNTAX     Counter32
					MAX-ACCESS read-only
					STATUS     current
					DESCRIPTION
				        	"The number of portal page request success number based on the SSID."
					::= { dot11SsidTeminalEntry 2 }										
					
pSsidUserRedirReqSuccRate		OBJECT-TYPE
					SYNTAX     INTEGER
					MAX-ACCESS read-only
					STATUS     current
					DESCRIPTION
				        	"The number of portal page request success rate based on the SSID."
					::= { dot11SsidTeminalEntry 3 }	
					
pSsidRadiusAuthReqNum			OBJECT-TYPE
					SYNTAX     Counter32
					MAX-ACCESS read-only
					STATUS     current
					DESCRIPTION
				        	"The number of radius authentication request number based on the SSID."
					::= { dot11SsidTeminalEntry 4 }		
					
pSsidRadiusAuthReqSuccNum		OBJECT-TYPE
					SYNTAX     Counter32
					MAX-ACCESS read-only
					STATUS     current
					DESCRIPTION
				        	"The number of radius authentication request success number based on the SSID."
					::= { dot11SsidTeminalEntry 5 }														

pSsidRadiusAuthReqSuccRate		OBJECT-TYPE
					SYNTAX     INTEGER
					MAX-ACCESS read-only
					STATUS     current
					DESCRIPTION
				        	"The number of radius authentication request success rate based on the SSID."
					::= { dot11SsidTeminalEntry 6 }	
					
pSsidChallengeReqNum			OBJECT-TYPE
					SYNTAX     Counter32
					MAX-ACCESS read-only
					STATUS     current
					DESCRIPTION
				        	"The number of challenge request number based on the SSID."
					::= { dot11SsidTeminalEntry 7 }		
					
pSsidChallengeReqSuccNum		OBJECT-TYPE
					SYNTAX     Counter32
					MAX-ACCESS read-only
					STATUS     current
					DESCRIPTION
				        	"The number of challenge request success number based on the SSID."
					::= { dot11SsidTeminalEntry 8 }	
					
pSsidChallengeReqSuccRate		OBJECT-TYPE
					SYNTAX     INTEGER
					MAX-ACCESS read-only
					STATUS     current
					DESCRIPTION
				        	"The number of challenge request success rate based on the SSID."
					::= { dot11SsidTeminalEntry 9 }	
					
pSsidReqnum				OBJECT-TYPE
					SYNTAX     Counter32
					MAX-ACCESS read-only
					STATUS     current
					DESCRIPTION
				        	"The number of portal request number based on the SSID."
					::= { dot11SsidTeminalEntry 10 }
										
pSsidReqsuccnum				OBJECT-TYPE
					SYNTAX     Counter32
					MAX-ACCESS read-only
					STATUS     current
					DESCRIPTION
				        	"The number of portal request success number based on the SSID."
					::= { dot11SsidTeminalEntry 11 }																							

pSsidReqSuccRate			OBJECT-TYPE
					SYNTAX     INTEGER
					MAX-ACCESS read-only
					STATUS     current
					DESCRIPTION
				        	"The number of portal request success rate based on the SSID."
					::= { dot11SsidTeminalEntry 12 }										

--*******************************************************************************************************************************************************************
dot11NeighborAPTable OBJECT-TYPE
	    SYNTAX      SEQUENCE OF Dot11NeighborAPEntry
	    MAX-ACCESS  not-accessible
	    STATUS      current
	    DESCRIPTION
	        "This table shows neighbor AP."
	    ::= { wtpNeighbor 1 }

dot11NeighborAPEntry  OBJECT-TYPE
    SYNTAX      Dot11NeighborAPEntry
    MAX-ACCESS  not-accessible
    STATUS      current
    DESCRIPTION
        "Neighbor AP."
    INDEX { wtpMacAddr,
		neighborAPIndex }
    ::= { dot11NeighborAPTable 1 }
Dot11NeighborAPEntry ::=SEQUENCE{
		neighborAPIndex			INTEGER,
		neighborAPMac			DisplayString,
		neighborAPRate			INTEGER,
		neighborAPChannel		INTEGER,
		neighborAPRssi			INTEGER,
		neighborAPNoise			INTEGER,
		neighborAPBeaconInterval	INTEGER,
		neighborAPCapability		INTEGER,
		neighborAPEssid			DisplayString,
		neighborAPElemInfo		DisplayString,
		neighborAPSignalIntensity       INTEGER
}

neighborAPIndex				OBJECT-TYPE
					SYNTAX     INTEGER
					MAX-ACCESS read-only
					STATUS     current
					DESCRIPTION
						"Rogue AP index"
					::= { dot11NeighborAPEntry 1 }

neighborAPMac				OBJECT-TYPE
					SYNTAX     DisplayString
					MAX-ACCESS read-only
					STATUS     current
					DESCRIPTION
						"Rogue AP mac"
					::= { dot11NeighborAPEntry 2 }

neighborAPRate				OBJECT-TYPE
					SYNTAX     INTEGER
					MAX-ACCESS read-only
					STATUS     current
					DESCRIPTION
						"Rogue AP rate"
					::= { dot11NeighborAPEntry 3 }

neighborAPChannel				OBJECT-TYPE
					SYNTAX     INTEGER
					MAX-ACCESS read-only
					STATUS     current
					DESCRIPTION
						"Rogue AP channel"
					::= { dot11NeighborAPEntry 4 }

neighborAPRssi				OBJECT-TYPE
					SYNTAX     INTEGER
					MAX-ACCESS read-only
					STATUS     current
					DESCRIPTION
						"Rogue AP rssi"
					::= { dot11NeighborAPEntry 5 }

neighborAPNoise				OBJECT-TYPE
					SYNTAX     INTEGER
					MAX-ACCESS read-only
					STATUS     current
					DESCRIPTION
						"Rogue AP noise"
					::= { dot11NeighborAPEntry 6 }

neighborAPBeaconInterval			OBJECT-TYPE
					SYNTAX     INTEGER
					MAX-ACCESS read-only
					STATUS     current
					DESCRIPTION
						"Rogue AP beacon interval"
					::= { dot11NeighborAPEntry 7 }
neighborAPCapability			OBJECT-TYPE
					SYNTAX     INTEGER
					MAX-ACCESS read-only
					STATUS     current
					DESCRIPTION
						"Rogue AP capability"
					::= { dot11NeighborAPEntry 8 }

neighborAPEssid				OBJECT-TYPE
					SYNTAX     DisplayString
					MAX-ACCESS read-only
					STATUS     current
					DESCRIPTION
						"Rogue AP essid"
					::= { dot11NeighborAPEntry 9 }

neighborAPElemInfo				OBJECT-TYPE
					SYNTAX     DisplayString
					MAX-ACCESS read-only
					STATUS     current
					DESCRIPTION
						"Rogue AP element info"
					::= { dot11NeighborAPEntry 10 }

neighborAPSignalIntensity				OBJECT-TYPE
					SYNTAX     INTEGER
					MAX-ACCESS read-only
					STATUS     current
					DESCRIPTION
						"Rogue AP SignalIntensity"
					::= { dot11NeighborAPEntry 11 }
					
					
					




dot11NewNeighborAPTable OBJECT-TYPE
	    SYNTAX      SEQUENCE OF Dot11NewNeighborAPEntry
	    MAX-ACCESS  not-accessible
	    STATUS      current
	    DESCRIPTION
	        "This table shows new neighbor AP."
	    ::= { wtpNeighbor 2 }

dot11NewNeighborAPEntry  OBJECT-TYPE
    SYNTAX      Dot11NewNeighborAPEntry
    MAX-ACCESS  not-accessible
    STATUS      current
    DESCRIPTION
        "NewNeighbor AP."
    INDEX { wtpMacAddr,
              wtpWirelessIfIndex,
		neighborAPIndex }
    ::= { dot11NewNeighborAPTable 1 }
Dot11NewNeighborAPEntry ::=SEQUENCE{
		NewneighborAPMac			DisplayString,
		NewneighborAPRate			INTEGER,
		NewneighborAPChannel		        INTEGER,
		NewneighborAPRssi			INTEGER,
		NewneighborAPNoise			INTEGER,
		NewneighborAPBeaconInterval	        INTEGER,
		NewneighborAPCapability		        INTEGER,
		NewneighborAPEssid			DisplayString,
		NewneighborAPElemInfo		        DisplayString,
		NewneighborAPSignalIntensity            INTEGER
}


NewneighborAPMac				OBJECT-TYPE
					SYNTAX     DisplayString
					MAX-ACCESS read-only
					STATUS     current
					DESCRIPTION
						"Rogue AP mac"
					::= { dot11NewNeighborAPEntry 1 }

NewneighborAPRate				OBJECT-TYPE
					SYNTAX     INTEGER
					MAX-ACCESS read-only
					STATUS     current
					DESCRIPTION
						"Rogue AP rate"
					::= { dot11NewNeighborAPEntry 2 }

NewneighborAPChannel				OBJECT-TYPE
					SYNTAX     INTEGER
					MAX-ACCESS read-only
					STATUS     current
					DESCRIPTION
						"Rogue AP channel"
					::= { dot11NewNeighborAPEntry 3 }

NewneighborAPRssi				OBJECT-TYPE
					SYNTAX     INTEGER
					MAX-ACCESS read-only
					STATUS     current
					DESCRIPTION
						"Rogue AP rssi"
					::= { dot11NewNeighborAPEntry 4 }

NewneighborAPNoise				OBJECT-TYPE
					SYNTAX     INTEGER
					MAX-ACCESS read-only
					STATUS     current
					DESCRIPTION
						"Rogue AP noise"
					::= { dot11NewNeighborAPEntry 5 }

NewneighborAPBeaconInterval			OBJECT-TYPE
					SYNTAX     INTEGER
					MAX-ACCESS read-only
					STATUS     current
					DESCRIPTION
						"Rogue AP beacon interval"
					::= { dot11NewNeighborAPEntry 6 }
NewneighborAPCapability			OBJECT-TYPE
					SYNTAX     INTEGER
					MAX-ACCESS read-only
					STATUS     current
					DESCRIPTION
						"Rogue AP capability"
					::= { dot11NewNeighborAPEntry 7 }

NewneighborAPEssid				OBJECT-TYPE
					SYNTAX     DisplayString
					MAX-ACCESS read-only
					STATUS     current
					DESCRIPTION
						"Rogue AP essid"
					::= { dot11NewNeighborAPEntry 8 }

NewneighborAPElemInfo				OBJECT-TYPE
					SYNTAX     DisplayString
					MAX-ACCESS read-only
					STATUS     current
					DESCRIPTION
						"Rogue AP element info"
					::= { dot11NewNeighborAPEntry 9 }

NewneighborAPSignalIntensity				OBJECT-TYPE
					SYNTAX     INTEGER
					MAX-ACCESS read-only
					STATUS     current
					DESCRIPTION
						"Rogue AP SignalIntensity"
					::= { dot11NewNeighborAPEntry 10 }



--********************************************************************************************
wtpInnerTrap OBJECT IDENTIFIER
		::={ dot11WtpTrap 0 }
		
wtpAplicationTrap OBJECT IDENTIFIER
		::={ dot11WtpTrap 1 }

wtpTrapDescription	 			OBJECT-TYPE
				SYNTAX     	DisplayString 
				MAX-ACCESS 	not-accessible
				STATUS     	current
				DESCRIPTION
			   "This variable displays content of Trap warning  as follow:
			   sequence of warnings,
			   element of network device,
			   level of warning,
			   type of warning,
			   causes of warning (optional)	,
			   time of warning occurs,
			   status of warning,
			   title of warning,
			   content of warning"
				::= { dot11WtpTrap 2 }
SSIDTrapDescription	 			OBJECT-TYPE
				SYNTAX     	DisplayString 
				MAX-ACCESS 	not-accessible
				STATUS     	current
				DESCRIPTION
			   "This variable shows the SSID of trap"
				::= { dot11WtpTrap 3 }
BSSIDTrapDescription	 			OBJECT-TYPE
				SYNTAX     	DisplayString 
				MAX-ACCESS 	not-accessible
				STATUS     	current
				DESCRIPTION
			   "This variable shows the BSSID of trap"
				::= { dot11WtpTrap 4 }
RadioInfoTrapDescription	 			OBJECT-TYPE
				SYNTAX     	DisplayString 
				MAX-ACCESS 	not-accessible
				STATUS     	current
				DESCRIPTION
			   "This variable shows the Radio interface info of trap"
				::= { dot11WtpTrap 5 }
MaxUserTrapDescription	 			OBJECT-TYPE
				SYNTAX     	DisplayString 
				MAX-ACCESS 	not-accessible
				STATUS     	current
				DESCRIPTION
			   "This variable shows the Ap Max users of trap"
				::= { dot11WtpTrap 6 }
UserAssocFailedReasonTrapDescription	 			OBJECT-TYPE
				SYNTAX     	DisplayString 
				MAX-ACCESS 	not-accessible
				STATUS     	current
				DESCRIPTION
			   "This variable shows the user associate failed reason of trap"
				::= { dot11WtpTrap 7 }
ApDownReasonTrapDescription	 			OBJECT-TYPE
				SYNTAX     	DisplayString 
				MAX-ACCESS 	not-accessible
				STATUS     	current
				DESCRIPTION
			   "This variable shows the Ap down reason of trap"
				::= { dot11WtpTrap 8 }
InterfOppBSSIDTrapDescription	 			OBJECT-TYPE
				SYNTAX     	DisplayString 
				MAX-ACCESS 	not-accessible
				STATUS     	current
				DESCRIPTION
			   "This variable shows the interfere resource BSSID of trap"
				::= { dot11WtpTrap 9 }
SecurityIndexTrapDescription	 			OBJECT-TYPE
				SYNTAX     	DisplayString 
				MAX-ACCESS 	not-accessible
				STATUS     	current
				DESCRIPTION
			   "This variable shows the security index of trap"
				::= { dot11WtpTrap 10 }		
InterfSecurityIndexTrapDescription	 			OBJECT-TYPE
				SYNTAX     	DisplayString 
				MAX-ACCESS 	not-accessible
				STATUS     	current
				DESCRIPTION
			   "This variable shows the interfere security index of trap"
				::= { dot11WtpTrap 11 }
APOffLineReasonTrapDescription	 			OBJECT-TYPE
				SYNTAX     	DisplayString 
				MAX-ACCESS 	not-accessible
				STATUS     	current
				DESCRIPTION
			   "This variable shows the AP offline reason of trap"
				::= { dot11WtpTrap 12 }
APModeTrapDescription	 			OBJECT-TYPE
				SYNTAX     	DisplayString 
				MAX-ACCESS 	not-accessible
				STATUS     	current
				DESCRIPTION
			   "This variable shows the AP channel changed mode of trap"
				::= { dot11WtpTrap 13 }
APUpdateFailedReasonTrapDescription	 			OBJECT-TYPE
				SYNTAX     	DisplayString 
				MAX-ACCESS 	not-accessible
				STATUS     	current
				DESCRIPTION
			   "This variable shows the AP update failed reason of trap"
				::= { dot11WtpTrap 14 }
APUpdateVersionTrapDescription	 			OBJECT-TYPE
				SYNTAX     	DisplayString 
				MAX-ACCESS 	not-accessible
				STATUS     	current
				DESCRIPTION
			   "This variable shows the AP update version of trap"
				::= { dot11WtpTrap 15 }
APUpdatePreVersionTrapDescription	 			OBJECT-TYPE
				SYNTAX     	DisplayString 
				MAX-ACCESS 	not-accessible
				STATUS     	current
				DESCRIPTION
			   "This variable shows the AP update preversion of trap"
				::= { dot11WtpTrap 16 }
VerifyModeTrapDescription	 			OBJECT-TYPE
				SYNTAX     	DisplayString 
				MAX-ACCESS 	not-accessible
				STATUS     	current
				DESCRIPTION
			   "This variable shows the verify mode of trap"
				::= { dot11WtpTrap 17 }

-- Trap father node
--	The following content is about child node of trap

	wtpDownTrap NOTIFICATION-TYPE
		OBJECTS {
				wtpMacAddr
			}
		STATUS		current
		DESCRIPTION
			"An wtpDownTrap Trap signifies that there has been an signal of AP-SHUT-DOWN "
	::= { wtpInnerTrap 1 }
	
	wtpSysStartTrap NOTIFICATION-TYPE
		OBJECTS {
				wtpMacAddr
			}
		STATUS		current
		DESCRIPTION
			"An wtpSysStartTrap Trap signifies that there has been an signal of AP-REBOOT "
	::= { wtpInnerTrap 2 }
	
	wtpChannelModifiedTrap NOTIFICATION-TYPE
		OBJECTS {
				wtpMacAddr
			}
		STATUS		current
		DESCRIPTION
			"An wtpChannelModifiedTrap Trap signifies that there has been an signal of AP-CHANNEL-CHANGED "
	::= { wtpInnerTrap 3 }
	
	wtpChannelObstructionTrap NOTIFICATION-TYPE
		OBJECTS {
				wtpMacAddr
			}
		STATUS		current
		DESCRIPTION
			"An wtpChannelObstructionTrap Trap signifies that there has been an signal of CHANNEL-Obstruction "
	::= { wtpAplicationTrap 1 }
	
	wtpIPChangeAlarmTrap NOTIFICATION-TYPE
		OBJECTS {
				wtpMacAddr
			}
		STATUS		current
		DESCRIPTION
			"An wtpAPIPChangeAlarmTrap Trap signifies that there has been an signal of AP-IP-CHANGED "
	::= { wtpInnerTrap 4 }
	
	wtpFlashWriteFailTrap NOTIFICATION-TYPE
		OBJECTS {
				wtpMacAddr
			}
		STATUS		current
		DESCRIPTION
			"An wtpFlashWriteFailTrap Trap signifies that there has been an signal of AP-WRITE-CACHE-FAILED "
	::= { wtpInnerTrap 5 }
	
	wtpAPInterferenceDetectedTrap NOTIFICATION-TYPE
		OBJECTS {
				wtpMacAddr
			}
		STATUS		current
		DESCRIPTION
			"An wtpAPInterferenceDetectedTrap Trap signifies that there has been an signal of AP-CHANNEL-Obstruction "
	::= { wtpAplicationTrap 2 }
	
	wtpStaInterferenceDetectedTrap NOTIFICATION-TYPE
		OBJECTS {
				wtpMacAddr
			}
		STATUS		current
		DESCRIPTION
			"An wtpStaInterferenceDetectedTrap Trap signifies that there has been an signal of TERMINAL-CHANNEL-Obstruction "
	::= { wtpAplicationTrap 3 }
	
	wtpDeviceInterferenceDetectedTrap NOTIFICATION-TYPE
		OBJECTS {
				wtpMacAddr
			}
		STATUS		current
		DESCRIPTION
			"An wtpDeviceInterferenceDetectedTrap Trap signifies that there has been an signal of DEVICE-CHANNEL-Obstruction "
	::= { wtpAplicationTrap 4 }
	
	wtpSubscriberDatabaseFullTrap NOTIFICATION-TYPE
		OBJECTS {
				wtpMacAddr
			}
		STATUS		current
		DESCRIPTION
			"An wtpSubscriberDatabaseFullTrap Trap signifies that there has been an signal of ADD-MIDIFY-USER-FAILED "
	::= { wtpAplicationTrap 5 }
	
	wtpDFSFreeCountBelowThresholdTrap NOTIFICATION-TYPE
		OBJECTS {
				wtpMacAddr
			}
		STATUS		current
		DESCRIPTION
			"An wtpDFSFreeCountBelowThresholdTrap Trap signifies that there has been an signal of CHANNEL-NUMBER-LOWER "
	::= { wtpAplicationTrap 6 }
	
	wtpColdStartTrap NOTIFICATION-TYPE
		OBJECTS {
				wtpMacAddr
			}
		STATUS		current
		DESCRIPTION
			"An wtpColdStartTrap Trap signifies that there has been an signal of Cold-Start "
	::= { wtpInnerTrap 6 }
	
	wtpAuthModeChangeTrap NOTIFICATION-TYPE
		OBJECTS {
				wtpMacAddr
			}
		STATUS		current
		DESCRIPTION
			"An wtpAuthModeChangeTrap Trap signifies that there has been an signal of Auth-Mode_change "
	::= { wtpInnerTrap 7 }
	
	wtpPreSharedKeyChangeTrap NOTIFICATION-TYPE
		OBJECTS {
				wtpMacAddr
			}
		STATUS		current
		DESCRIPTION
			"An wtpPreSharedKeyChangeTrap Trap signifies that there has been an signal of PreSharedKey-Changed "
	::= { wtpInnerTrap 8 }
	
	wtpElectrifyRegisterCircleTrap NOTIFICATION-TYPE
		OBJECTS {
				wtpMacAddr
			}
		STATUS		current
		DESCRIPTION
			"An wtpElectrifyRegisterCircleTrap Trap signifies that there has been an signal of Electrify-RegisterCircle "
	::= { wtpInnerTrap 9 }
	
	wtpFileTransferTrap NOTIFICATION-TYPE
		OBJECTS {
				wtpMacAddr
			}
		STATUS		current
		DESCRIPTION
			"An wtpFileTransferTrap Trap signifies that there has been an signal of File-Transfered "
	::= { wtpAplicationTrap 7 }
	
	
	wtpAPUpdateTrap NOTIFICATION-TYPE
		OBJECTS {
				wtpMacAddr
			}
		STATUS		current
		DESCRIPTION
			"An wtpAPUpdateTrap Trap signifies that there has been an signal of Configure-Upload-Load "
	::= { wtpInnerTrap 10 }
	
	wtpCoverholeTrap NOTIFICATION-TYPE
		OBJECTS {
				wtpMacAddr
			}
		STATUS		current
		DESCRIPTION
			"An wtpCoverholeTrap Trap signifies that there has been an signal of AP-COVERED-HOLE "
	::= { wtpInnerTrap 11 }
	
	wtpStationOffLineTrap NOTIFICATION-TYPE
		OBJECTS {
				wtpMacAddr
			}
		STATUS		current
		DESCRIPTION
			"An wtpStationOffLineTrap Trap signifies that there has been an signal of Station-Off-Line "
	::= { wtpAplicationTrap 8 }
	
	wtpSolveLinkVarifiedTrap NOTIFICATION-TYPE
		OBJECTS {
				wtpMacAddr
			}
		STATUS		current
		DESCRIPTION
			"An wtpSolveLinkVarifiedTrap Trap signifies that there has been an signal of Solve-Link-Varified "
	::= { wtpAplicationTrap 9 }
	
	wtpLinkVarifyFailedTrap NOTIFICATION-TYPE
		OBJECTS {
				wtpMacAddr
			}
		STATUS		current
		DESCRIPTION
			"An wtpLinkVarifyFailedTrap Trap signifies that there has been an signal of Link-Varified-Failed "
	::= { wtpAplicationTrap 10 }
	
	wtpStationOnLineTrap NOTIFICATION-TYPE
		OBJECTS {
				wtpMacAddr
			}
		STATUS		current
		DESCRIPTION
			"An wtpStationOnLineTrap Trap signifies that there has been an signal of Station-Online "
	::= { wtpAplicationTrap 11 }
	
	wtpWirePortExceptionTrap NOTIFICATION-TYPE
		OBJECTS {
				wtpMacAddr
			}
		STATUS		current
		DESCRIPTION
			"An wtpWirePortExceptionTrap Trap signifies that there has been an signal of AP-WIRELESS-PORT-EXCEPTION "
	::= { wtpInnerTrap 12 }
	
	CPUusageTooHighTrap NOTIFICATION-TYPE
		OBJECTS {
				wtpMacAddr
			}
		STATUS		current
		DESCRIPTION
			"An CPUusageTooHighTrap Trap signifies that there has been an signal of AP-CPU-USAGE-TOO-HIGH "
	::= { wtpInnerTrap 13 }
	
	CPUusageTooHighRecovTrap NOTIFICATION-TYPE
		OBJECTS {
				wtpMacAddr
			}
		STATUS		current
		DESCRIPTION
			"An CPUusageTooHighRecovTrap Trap signifies that there has been an signal of AP-CPU-USAGE-TOO-HIGH-RECOVERED "
	::= { wtpInnerTrap 14 }
	
	MemUsageTooHighTrap NOTIFICATION-TYPE
		OBJECTS {
				wtpMacAddr
			}
		STATUS		current
		DESCRIPTION
			"An MemUsageTooHighTrap Trap signifies that there has been an signal of AP-MEM-USAGE-TOO-HIGH "
	::= { wtpInnerTrap 15 }
	
	MemUsageTooHighRecovTrap NOTIFICATION-TYPE
		OBJECTS {
				wtpMacAddr
			}
		STATUS		current
		DESCRIPTION
			"An MemUsageTooHighRecovTrap Trap signifies that there has been an signal of AP-MEM-USAGE-TOO-HIGH-RECOVER "
	::= { wtpInnerTrap 16 }
	
	TemperTooHighTrap NOTIFICATION-TYPE
		OBJECTS {
				wtpMacAddr
			}
		STATUS		current
		DESCRIPTION
			"An TemperTooHighTrap Trap signifies that there has been an signal of AP-TEMPERETURE-TOO-HIGH "
	::= { wtpInnerTrap 17 }
	
	TemperTooHighRecoverTrap NOTIFICATION-TYPE
		OBJECTS {
				wtpMacAddr
			}
		STATUS		current
		DESCRIPTION
			"An TemperTooHighRecoverTrap Trap signifies that there has been an signal of AP-TEMPERETURE-TOO-HIGH-RECOVER "
	::= { wtpInnerTrap 18 }
	
	APMtWorkModeChgTrap NOTIFICATION-TYPE
		OBJECTS {
				wtpMacAddr
			}
		STATUS		current
		DESCRIPTION
			"An APMtWorkModeChgTrap Trap signifies that there has been an signal of AP-MT-WORKMODE-CHANGE "
	::= { wtpInnerTrap 19 }
	
	APswitchBetweenACTrap NOTIFICATION-TYPE
		OBJECTS {
				wtpMacAddr
			}
		STATUS		current
		DESCRIPTION
			"An APswitchBetweenACTrap Trap signifies that there has been an signal of AP-SWITCH-BETWEEN-DIF-AC "
	::= { wtpInnerTrap 20 }
	
	SSIDkeyConflictTrap NOTIFICATION-TYPE
		OBJECTS {
				wtpMacAddr
			}
		STATUS		current
		DESCRIPTION
			"An SSIDkeyConflictTrap Trap signifies that there has been an signal of AP-SSID-KEY-CONFLICT "
	::= { wtpInnerTrap 21 }
	
-- add app trap in guangzhou mobile 

	APInterfClearTrap NOTIFICATION-TYPE
		OBJECTS {
				wtpMacAddr
			}
		STATUS		current
		DESCRIPTION
			"An APInterfClearTrap Trap signifies that there has been an signal of AP-INTERF-NEARBY-CLEAR "
	::= { wtpAplicationTrap 12 }
	
	APStaInterfClearTrap NOTIFICATION-TYPE
		OBJECTS {
				wtpMacAddr
			}
		STATUS		current
		DESCRIPTION
			"An APStaInterfClearTrap Trap signifies that there has been an signal of AP-STA-INTERF-CLEAR "
	::= { wtpAplicationTrap 13 }
	
	APOtherDeviceInterfDetectedTrap NOTIFICATION-TYPE
		OBJECTS {
				wtpMacAddr
			}
		STATUS		current
		DESCRIPTION
			"An APInterfClearTrap Trap signifies that there has been an signal of AP-OTHER-DEVICE-INTERF-DETECTED "
	::= { wtpAplicationTrap 14 }
	
	APOtherDevInterfClearTrap NOTIFICATION-TYPE
		OBJECTS {
				wtpMacAddr
			}
		STATUS		current
		DESCRIPTION
			"An APOtherDevInterfClearTrap Trap signifies that there has been an signal of AP-OTHER-DEVICE-INTERF-CLEAR "
	::= { wtpAplicationTrap 15 }
	
	APModuleTroubleTrap NOTIFICATION-TYPE
		OBJECTS {
				wtpMacAddr
			}
		STATUS		current
		DESCRIPTION
			"An APModuleTroubleTrap Trap signifies that there has been an signal of AP-MODULE-TROUBLE "
	::= { wtpAplicationTrap 16 }
	
	APModuleTroubleClearTrap NOTIFICATION-TYPE
		OBJECTS {
				wtpMacAddr
			}
		STATUS		current
		DESCRIPTION
			"An APModuleTroubleClearTrap Trap signifies that there has been an signal of AP-MODULE-TROUBLE-CLEAR "
	::= { wtpAplicationTrap 17 }
	
	APRadioDownTrap NOTIFICATION-TYPE
		OBJECTS {
				wtpMacAddr
			}
		STATUS		current
		DESCRIPTION
			"An APRadioDownTrap Trap signifies that there has been an signal of AP-RADIO-DOWN "
	::= { wtpAplicationTrap 18 }
	
	APRadioDownRecovTrap NOTIFICATION-TYPE
		OBJECTS {
				wtpMacAddr
			}
		STATUS		current
		DESCRIPTION
			"An APRadioDownRecovTrap Trap signifies that there has been an signal of AP-RADIO-DOWN-CLEAR "
	::= { wtpAplicationTrap 19 }
	
	APTLAuthenticationFailedTrap NOTIFICATION-TYPE
		OBJECTS {
				wtpMacAddr
			}
		STATUS		current
		DESCRIPTION
			"An APTLAuthenticationFailedTrap Trap signifies that there has been an signal of AP-TL-Authentication-FAILED "
	::= { wtpAplicationTrap 20 }
	
	APStaAuthErrorTrap NOTIFICATION-TYPE
		OBJECTS {
				wtpMacAddr
			}
		STATUS		current
		DESCRIPTION
			"An APStaAuthErrorTrap Trap signifies that there has been an signal of AP-STA-AUTH-ERROR "
	::= { wtpAplicationTrap 21 }
	
	APStAssociationFailTrap NOTIFICATION-TYPE
		OBJECTS {
				wtpMacAddr
			}
		STATUS		current
		DESCRIPTION
			"An APStAssociationFailTrap Trap signifies that there has been an signal of AP-STA-ASSOCIATION-FAILED "
	::= { wtpAplicationTrap 22 }
	
	APUserWithInvalidCerInbreakNetTrap NOTIFICATION-TYPE
		OBJECTS {
				wtpMacAddr
			}
		STATUS		current
		DESCRIPTION
			"An APUserWithInvalidCerInbreakNetTrap Trap signifies that there has been an signal of AP-USER-WITH-INVALID-CERTIFECATION-INBREAK-NETWORK "
	::= { wtpAplicationTrap 23 }
	
	APStationRepititiveAttackTrap NOTIFICATION-TYPE
		OBJECTS {
				wtpMacAddr
			}
		STATUS		current
		DESCRIPTION
			"An APStationRepititiveAttackTrap Trap signifies that there has been an signal of AP-STATION-REPITITION-ATTACK "
	::= { wtpAplicationTrap 24 }
	
	APTamperAttackTrap NOTIFICATION-TYPE
		OBJECTS {
				wtpMacAddr
			}
		STATUS		current
		DESCRIPTION
			"An APTamperAttackTrap Trap signifies that there has been an signal of AP-TAMPER-ATTACK "
	::= { wtpAplicationTrap 25 }
	
	APLowSafeLevelAttackTrap NOTIFICATION-TYPE
		OBJECTS {
				wtpMacAddr
			}
		STATUS		current
		DESCRIPTION
			"An APLowSafeLevelAttackTrap Trap signifies that there has been an signal of AP-LOW-SAFE-LEVEL-ATTACK "
	::= { wtpAplicationTrap 26 }
	
	APAddressRedirectionAttackTrap NOTIFICATION-TYPE
		OBJECTS {
				wtpMacAddr
			}
		STATUS		current
		DESCRIPTION
			"An APAddressRedirectionAttackTrap Trap signifies that there has been an signal of AP-ADDRESS-REDIRECTION-ATTACK "
	::= { wtpAplicationTrap 27 }
	
	APMeshAuthFailureTrap NOTIFICATION-TYPE
		OBJECTS {
				wtpMacAddr
			}
		STATUS		current
		DESCRIPTION
			"An APMeshAuthFailureTrap Trap signifies that there has been an signal of AP-MESH-AUTH-FAILED "
	::= { wtpAplicationTrap 28 }
	
	APChildExcludedParentTrap NOTIFICATION-TYPE
		OBJECTS {
				wtpMacAddr
			}
		STATUS		current
		DESCRIPTION
			"An APChildExcludedParentTrap Trap signifies that there has been an signal of AP-CHILD-EXCLUDED-PARENT "
	::= { wtpAplicationTrap 29 }
	
	APParentChangeTrap NOTIFICATION-TYPE
		OBJECTS {
				wtpMacAddr
			}
		STATUS		current
		DESCRIPTION
			"An APParentChangeTrap Trap signifies that there has been an signal of AP-PARENT-CHANGE "
	::= { wtpAplicationTrap 30 }
	
	APChildMovedTrap NOTIFICATION-TYPE
		OBJECTS {
				wtpMacAddr
			}
		STATUS		current
		DESCRIPTION
			"An APChildMovedTrap Trap signifies that there has been an signal of AP-CHILD-MOVED "
	::= { wtpAplicationTrap 31 }
	
	APExcessiveParentChangeTrap NOTIFICATION-TYPE
		OBJECTS {
				wtpMacAddr
			}
		STATUS		current
		DESCRIPTION
			"An APExcessiveParentChangeTrap Trap signifies that there has been an signal of AP-EXCESSIVE-PARENT-CHANGE "
	::= { wtpAplicationTrap 32 }
	
	APMeshOnsetSNRTrap NOTIFICATION-TYPE
		OBJECTS {
				wtpMacAddr
			}
		STATUS		current
		DESCRIPTION
			"An APMeshOnsetSNRTrap Trap signifies that there has been an signal of AP-MESH-ON-SET "
	::= { wtpAplicationTrap 33 }
	
	APMeshAbateSNRTrap NOTIFICATION-TYPE
		OBJECTS {
				wtpMacAddr
			}
		STATUS		current
		DESCRIPTION
			"An APMeshAbateSNRTrap Trap signifies that there has been an signal of AP-MESH-ABATE "
	::= { wtpAplicationTrap 34 }
	
	APConsoleLoginTrap NOTIFICATION-TYPE
		OBJECTS {
				wtpMacAddr
			}
		STATUS		current
		DESCRIPTION
			"An APConsoleLoginTrap Trap signifies that there has been an signal of AP-CONSOLE-LOGIN "
	::= { wtpAplicationTrap 35 }
	
	APQueueOverflowTrap NOTIFICATION-TYPE
		OBJECTS {
				wtpMacAddr
			}
		STATUS		current
		DESCRIPTION
			"An APQueueOverflowTrap Trap signifies that there has been an signal of AP-QUEUE-OVER-FLOW "
	::= { wtpAplicationTrap 36 }
	
	wtpOnlineTrap NOTIFICATION-TYPE
		OBJECTS {
				wtpMacAddr
			}
		STATUS		current
		DESCRIPTION
			"An wtpOnlineTrap Trap signifies that there has been an signal of AP-ON-LINE "
	::= { wtpInnerTrap 22 }
	
	wtpOfflineTrap NOTIFICATION-TYPE
		OBJECTS {
				wtpMacAddr
			}
		STATUS		current
		DESCRIPTION
			"An wtpOfflineTrap Trap signifies that there has been an signal of AP-OFF-LINE "
	::= { wtpInnerTrap 23 }
	
	wtpCoverHoleClearTrap NOTIFICATION-TYPE
		OBJECTS {
				wtpMacAddr
			}
		STATUS		current
		DESCRIPTION
			"An wtpCoverHoleClearTrap Trap signifies that there has been an signal of AP-COVER-HOLE-CLEAR "
	::= { wtpInnerTrap 24 }
	
	wtpSoftWareUpdateSucceed NOTIFICATION-TYPE
		OBJECTS {
				wtpMacAddr
			}
		STATUS		current
		DESCRIPTION
			"An wtpSoftWareUpdateSucceed Trap signifies that there has been an signal of AP-SOFTWARE-UPDATE-SUCCEED "
	::= { wtpInnerTrap 25 }
	
	wtpSoftWareUpdateFailed NOTIFICATION-TYPE
		OBJECTS {
				wtpMacAddr
			}
		STATUS		current
		DESCRIPTION
			"An wtpSoftWareUpdateFailed Trap signifies that there has been an signal of AP-SOFTWARE-UPDATE-FAILED "
	::= { wtpInnerTrap 29 }

	wtpConfigurationErrorTrap NOTIFICATION-TYPE
		OBJECTS {
				wtpMacAddr
			}
		STATUS		current
		DESCRIPTION
			"An wtpConfigurationErrorTrap Trap signifies that there has been an signal of AP-Configuration-Error "
	::= { wtpInnerTrap 30 }
	
	ReservedReasonTrap NOTIFICATION-TYPE
		OBJECTS {
				wtpMacAddr
			}
		STATUS		current
		DESCRIPTION
			"Reserved of LTE FI quit reason "
	::= { wtpInnerTrap 31 }

	ACCTimeoutTrap NOTIFICATION-TYPE
		OBJECTS {
				wtpMacAddr
			}
		STATUS		current
		DESCRIPTION
			"ACCTimeout resulted in Lte Fi quit "
	::= { wtpInnerTrap 32 }

	ExtendReasonTrap NOTIFICATION-TYPE
		OBJECTS {
				wtpMacAddr
			}
		STATUS		current
		DESCRIPTION
			"extend reason of Lte Fi quit "
	::= { wtpInnerTrap 33 }	
	
	LteFiUplinkSwitchTrap NOTIFICATION-TYPE
		OBJECTS {
				wtpMacAddr
			}
		STATUS		current
		DESCRIPTION
			"extend reason of Lte Fi quit "
	::= { wtpInnerTrap 34 }		
	
	
	APAddUserFailClearTrap NOTIFICATION-TYPE
		OBJECTS {
				wtpMacAddr
			}
		STATUS		current
		DESCRIPTION
			"An APAddUserFailClearTrap Trap signifies that there has been an signal of AP-ADD-USER-FAIL-CLEAR "
	::= { wtpAplicationTrap 37 }
	
	APChannelTooLowClearTrap NOTIFICATION-TYPE
		OBJECTS {
				wtpMacAddr
			}
		STATUS		current
		DESCRIPTION
			"An APChannelTooLowClearTrap Trap signifies that there has been an signal of AP-CHANNEL-TOO-LOW-CLEAR "
	::= { wtpAplicationTrap 38 }
	
	APFindUnsafeESSID NOTIFICATION-TYPE
		OBJECTS {
				wtpMacAddr
			}
		STATUS		current
		DESCRIPTION
			"An APFindUnsafeESSID Trap signifies that there has been an signal of AP-FIND-UNSAFE-ESSID "
	::= { wtpAplicationTrap 39 }
	
	APFindSYNAttack NOTIFICATION-TYPE
		OBJECTS {
				wtpMacAddr
			}
		STATUS		current
		DESCRIPTION
			"An APFindSYNAttack Trap signifies that there has been an signal of AP-FIND-SYN-ATTACK "
	::= { wtpAplicationTrap 40 }

	ApNeighborChannelInterfTrap NOTIFICATION-TYPE
		OBJECTS {
				wtpMacAddr
			}
		STATUS		current
		DESCRIPTION
			"An ApNeighborChannelInterfTrap Trap signifies that there has been an signal of ap_neighbor_channel_interfere "
	::= { wtpAplicationTrap 41 }

	ApNeighborChannelInterfTrapClear NOTIFICATION-TYPE
		OBJECTS {
				wtpMacAddr
			}
		STATUS		current
		DESCRIPTION
			"An ApNeighborChannelInterfTrapClear Trap signifies that there has been an signal of ap_neighbor_channel_interfere_clear "
	::= { wtpAplicationTrap 42 }
	
	wtpStationOffLineAbnormalTrap NOTIFICATION-TYPE
		OBJECTS {
				wtpMacAddr
			}
		STATUS		current
		DESCRIPTION
			"An wtpStationOffLineAbnormalTrap Trap signifies that there has been an signal of station_leave_abnormal "
	::= { wtpAplicationTrap 44 }
	
	wtpUserLogoffAbnormalTrap NOTIFICATION-TYPE
		OBJECTS {
				wtpMacAddr
			}
		STATUS		current
		DESCRIPTION
			"An wtpUserLogoffAbnormalTrap Trap signifies that there has been an signal of user_logoff_abnormal "
	::= { wtpAplicationTrap 45 }

	wtpUserTrafficOverloadTrap NOTIFICATION-TYPE
		OBJECTS {
				wtpMacAddr
			}
		STATUS		current
		DESCRIPTION
			"An wtpUserTrafficOverloadTrap Trap signifies that there has been an signal of traffic overload "
	::= { wtpAplicationTrap 51 }

	wtpUnauthorizedStaMacTrap NOTIFICATION-TYPE
		OBJECTS {
				wtpMacAddr
			}
		STATUS		current
		DESCRIPTION
			"An wtpUnauthorizedStaMacTrap Trap signifies that there has been an signal of unauthorized station "
	::= { wtpAplicationTrap 52 }
END
