CAPWAP-BASE-MIB DEFINITIONS ::= BEGIN

IMPORTS

   PhysAddress, TEXTUAL-CONVENTION, TruthValue,
   DateAndTime, RowStatus
       FROM SNMPv2-TC
   InterfaceIndex
       FROM IF-MIB
   PhysicalIndex
       FROM ENTITY-MIB
   SnmpAdminString
       FROM SNMP-FRAMEWORK-MIB
   NOTIFICATION-GROUP, OBJECT-GROUP, MODULE-COMPLIANCE
       FROM SNMPv2-CONF
   MODULE-IDENTITY, OBJECT-TYPE, NOTIFICATION-TYPE, mib-2,
   Integer32, Unsigned32, Counter32
       FROM SNMPv2-SMI
   InetAddressType, InetAddress
       FROM INET-ADDRESS-MIB;

capwapBaseMIB MODULE-IDENTITY
    LAST-UPDATED "200811010000Z"        -- Nov 01th, 2008
    ORGANIZATION "IETF Control And Provisioning of Wireless Access
                  Points (CAPWAP) Working Group
                  http://www.ietf.org/html.charters/capwap-charter.html"
    CONTACT-INFO
        "General Discussion: capwap@frascone.com
         To Subscribe: http://lists.frascone.com/mailman/listinfo/capwap

         Yang Shi
         H3C, Digital Technology Plaza, NO.9 Shangdi 9th Street,Haidian
         District,Beijing,China(100085)
         Email:  young@h3c.com

         David T. Perkins
         228 Bayview Dr

San Carlos, CA 94070
         USA
         Phone: +1 408 394-8702
         Email:  dperkins@snmpinfo.com

         Chris Elliott
         Cisco Systems, Inc.
         7025 Kit Creek Rd., P.O. Box 14987
         Research Triangle Park  27709
         USA
         Phone: +1 919-392-2146
         Email: chelliot@cisco.com

         Yong Zhang
         Fortinet, Inc.
         1090 Kifer Road
         Sunnyvale, CA 94086
         USA
         Email: yzhang@fortinet.com"

    DESCRIPTION
        "Copyright (C) 2008 The Internet Society.  This version of
         the MIB module is part of RFC xxx; see the RFC itself
         for full legal notices.

         This MIB module contains managed object definitions for
         the CAPWAP Protocol."
    REVISION    "200811010000Z"
    DESCRIPTION
        "Initial version published as RFC xxx"
         ::= { mib-2 0 }

-- Textual Conventions

CapwapBaseWtpIdTC ::= TEXTUAL-CONVENTION
                DISPLAY-HINT "128a"
    STATUS      current
    DESCRIPTION
        "Represents an unique identifier of a WTP instance.
         As usual, a serial number of WTP will be used."
    SYNTAX       OCTET STRING(SIZE(128))

CapwapBaseStationIdTC ::= TEXTUAL-CONVENTION
                DISPLAY-HINT "1x:"
    STATUS      current
    DESCRIPTION
        "Represents an unique identifier of a station instance.
         As usual, the MAC address of station will be used."

SYNTAX      OCTET STRING (SIZE (6))

CapwapBaseRadioIdTC ::= TEXTUAL-CONVENTION
    DISPLAY-HINT "d"
    STATUS      current
    DESCRIPTION
        "Represents an unique identifier of a radio on a WTP."
    SYNTAX      Unsigned32 (1..31)

CapwapBaseTunnelModeTC ::= TEXTUAL-CONVENTION
    STATUS      current
    DESCRIPTION
        "Represents the tunneling modes of operation that are
         supported by the WTP.
         The WTP MAY support more than one option, represented by
         the bit field below.
           unused(0)        - This bit is unused
           localBridging(1) - Local Bridging Mode,
           dot3Tunnel(2)    - 802.3 Frame Tunnel Mode,
           nativeTunnel(3)  - Native Frame Tunnel Mode."
    REFERENCE
        "Section 4.6.42. of CAPWAP Protocol Specification, RFC xxx."
    SYNTAX      BITS {
                  unused(0),
                  localBridging(1),
                  dot3Tunnel(2),
                  nativeTunnel(3)
                }

CapwapBaseMacTypeTC ::= TEXTUAL-CONVENTION
    STATUS      current
    DESCRIPTION
        "Represents the MAC mode of operation supported by the WTP.
         The following enumerated values are supported:
           localMAC(0) - Local-MAC Mode,
           splitMAC(1) - Split-MAC Mode,
           both(2)     - Both Local-MAC and Split-MAC."
    REFERENCE
        "Section 4.6.43. of CAPWAP Protocol Specification, RFC xxx."
    SYNTAX      INTEGER {
                  localMAC(0),
                  splitMAC(1),
                  both(2)
                }

CapwapBaseChannelTypeTC::= TEXTUAL-CONVENTION
    STATUS      current
    DESCRIPTION


"Represents the channel type for CAPWAP protocol.
         The following enumerated values are supported:
           data(1)    - data Channel
           control(2) - control Channel."
    SYNTAX      INTEGER {
                  data(1),
                  control(2)
                }

CapwapBaseAuthenMethodTC ::= TEXTUAL-CONVENTION
    STATUS      current
    DESCRIPTION
        "Represents the authentication credential type
         for WTP.
         The following enumerated values are supported:
           other(1) - Other method, for example, vendor specific.
           clear(2) - Clear text and no authentication,
           x509(3)  - X.509 Certificate authentication,
           psk(4)   - Pre-Shared Secret authentication,
         As mandatory requirement, CAPWAP control channel
         authentication should use DTLS, and either by certificate or
         PSK. For data channel, DTLS is optional."
    SYNTAX      INTEGER {
                  other(1),
                  clear(2),
                  x509(3),
                  psk(4)
                }

-- Top level components of this MIB

-- Notifications
capwapBaseNotifications OBJECT IDENTIFIER
    ::= { capwapBaseMIB 0 }
-- Tables, Scalars
capwapBaseObjects OBJECT IDENTIFIER
    ::= { capwapBaseMIB 1 }
-- Conformance
capwapBaseConformance OBJECT IDENTIFIER
    ::= { capwapBaseMIB 2 }


-- AC Objects Group

capwapBaseAc OBJECT IDENTIFIER
    ::= { capwapBaseObjects 1 }

capwapBaseWtpSessions OBJECT-TYPE
SYNTAX      Unsigned32 (0..65535)
    MAX-ACCESS  read-only
    STATUS      current
    DESCRIPTION
        "Represents the total number of WTPs which are connecting to
         AC."
    REFERENCE
        "Section 4.6.1. of CAPWAP Protocol Specification, RFC xxx."
    ::= { capwapBaseAc 1 }

capwapBaseWtpSessionsLimit  OBJECT-TYPE
    SYNTAX      Unsigned32 (0..65535)
    MAX-ACCESS  read-write
    STATUS      current
    DESCRIPTION
        "Represents the maximum number of WTP sessions configured for
         the AC."
    REFERENCE
        "Section 4.6.1. of CAPWAP Protocol Specification, RFC xxx."
    ::= { capwapBaseAc 2 }

capwapBaseStationSessions  OBJECT-TYPE
    SYNTAX      Unsigned32 (0..65535)
    MAX-ACCESS  read-only
    STATUS      current
    DESCRIPTION
        "Represents the total number of stations which are accessing
         the wireless service provided by the AC."
    REFERENCE
        "Section 4.6.1. of CAPWAP Protocol Specification, RFC xxx."
    ::= { capwapBaseAc 3 }

capwapBaseStationSessionsLimit  OBJECT-TYPE
    SYNTAX      Unsigned32 (0..65535)
    MAX-ACCESS  read-write
    STATUS      current
    DESCRIPTION
        "Represents the maximum number of station sessions configured
         for the AC."
    REFERENCE
        "Section 4.6.1. of CAPWAP Protocol Specification, RFC xxx."
    ::= { capwapBaseAc 4 }

capwapBaseDataChannelSecOptions  OBJECT-TYPE
    SYNTAX      BITS {
                  other(0),
                  clear(1),
                  dtls(2)

  }
    MAX-ACCESS  read-only
    STATUS      current
    DESCRIPTION
        "Represents the security policy supported for CAPWAP data
         channel.
         The AC MAY support more than one option, represented by the bit
         field below.
           other(0) -  Other method, for example, vendor specific.
           clear(1) -  Clear Text,
           dtls(2)  -  DTLS."
    REFERENCE
       "Section 4.6.1. of CAPWAP Protocol Specification, RFC xxx."
    ::= { capwapBaseAc 5 }

capwapBaseDataChannelSecConfig  OBJECT-TYPE
    SYNTAX      BITS {
                  other(0),
                  clear(1),
                  dtls(2)
                }
    MAX-ACCESS  read-write
    STATUS      current
    DESCRIPTION
        "Represents the security policy configured for the AC for
         CAPWAP data channel.
         The configuration is represented by one of the bit
         fields below.
           other(0) -  Other method, for example, vendor specific.
           clear(1) -  Clear Text,
           dtls(2)  -  DTLS."
    REFERENCE
       "Section 4.6.1. of CAPWAP Protocol Specification, RFC xxx."
    ::= { capwapBaseAc 6 }

capwapBaseControlChannelAuthenOptions  OBJECT-TYPE
    SYNTAX      BITS {
                  unused(0),
                  x509(1),
                  psk(2)
                }
    MAX-ACCESS  read-only
    STATUS      current
    DESCRIPTION
        "Represents the authentication credential type supported by the
         AC for control channel.
         The AC MAY support more than one option, represented by the bit
         field below.



 unused(0) -  This bit is unused
           x509(1)   -  X.509 Certificate Based
           psk(2)    -  Pre-Shared Secret."
    REFERENCE
       "Section 4.6.1. of CAPWAP Protocol Specification, RFC xxx."
    ::= { capwapBaseAc 7 }

capwapBaseControlChannelAuthenConfig  OBJECT-TYPE
    SYNTAX      BITS {
                  unused(0),
                  x509(1),
                  psk(2)
                }
    MAX-ACCESS  read-write
    STATUS      current
    DESCRIPTION
        "Represents the authentication credential type configured for
         the AC for control channel.
         The configuration is represented by one of the bit
         fields below.
           unused(0) -  This bit is unused
           x509(1)   -  X.509 Certificate Based
           psk(2)    -  Pre-Shared Secret."
    REFERENCE
       "Section 4.6.1. of CAPWAP Protocol Specification, RFC xxx."
    ::= { capwapBaseAc 8 }

-- capwapBaseAcNameListTable table

capwapBaseAcNameListTable OBJECT-TYPE
    SYNTAX      SEQUENCE OF CapwapBaseAcNameListEntry
    MAX-ACCESS  not-accessible
    STATUS      current
    DESCRIPTION
        "A table of objects that display AC name list."
    ::= { capwapBaseAc 9 }

capwapBaseAcNameListEntry  OBJECT-TYPE
    SYNTAX      CapwapBaseAcNameListEntry
    MAX-ACCESS  not-accessible
    STATUS      current
    DESCRIPTION
        "A set of objects that configure AC name list.
         Values of all read-create objects in this
         table are persistent at restart/reboot."
    INDEX { capwapBaseAcNameListId }
    ::= { capwapBaseAcNameListTable 1 }


CapwapBaseAcNameListEntry ::= SEQUENCE {
      capwapBaseAcNameListId          Unsigned32,
      capwapBaseAcNameListName        OCTET STRING,
      capwapBaseAcNameListPriority    Unsigned32,
      capwapBaseAcNameListRowStatus   RowStatus
    }

capwapBaseAcNameListId OBJECT-TYPE
    SYNTAX      Unsigned32 (1..255)
    MAX-ACCESS  not-accessible
    STATUS      current
    DESCRIPTION
        "Represents a unique id for a AC Name list."
    ::= { capwapBaseAcNameListEntry 1 }

capwapBaseAcNameListName OBJECT-TYPE
    SYNTAX      OCTET STRING(SIZE(512))
    MAX-ACCESS  read-create
    STATUS      current
    DESCRIPTION
        "Represents the name of an AC."
    REFERENCE
        "Section 4.6.5. of CAPWAP Protocol Specification, RFC xxx."
    ::= { capwapBaseAcNameListEntry 2 }

capwapBaseAcNameListPriority OBJECT-TYPE
    SYNTAX      Unsigned32 (1..255)
    MAX-ACCESS  read-create
    STATUS      current
    DESCRIPTION
        "Represents the priority order of the preferred AC.
         For instance, the value of one (1) is used to set the primary
         AC, the value of two (2) is used to set the secondary, etc."
    REFERENCE
        "Section 4.6.5. of CAPWAP Protocol Specification, RFC xxx."
    ::= { capwapBaseAcNameListEntry 3 }

capwapBaseAcNameListRowStatus OBJECT-TYPE
    SYNTAX      RowStatus
    MAX-ACCESS  read-create
    STATUS      current
    DESCRIPTION
        "This variable is used to create, modify, and/or delete a row
         in this table."
    ::= { capwapBaseAcNameListEntry 4 }

-- End of capwapBaseAcNameListTable table
-- capwapBaseMacAclTable table

capwapBaseMacAclTable OBJECT-TYPE
    SYNTAX      SEQUENCE OF CapwapBaseMacAclEntry
    MAX-ACCESS  not-accessible
    STATUS      current
    DESCRIPTION
        "A table of objects that configure station Access Control
         List (ACL).
         WTP will not provide service to the MAC addresses configured
         in this table."
    ::= { capwapBaseAc 10 }

capwapBaseMacAclEntry  OBJECT-TYPE
    SYNTAX      CapwapBaseMacAclEntry
    MAX-ACCESS  not-accessible
    STATUS      current
    DESCRIPTION
        "A set of objects that configure station Access Control
         List (ACL).
         Values of all read-create objects in this
         table are persistent at AC restart/reboot."
    INDEX { capwapBaseMacAclId }
    ::= { capwapBaseMacAclTable 1 }

CapwapBaseMacAclEntry ::= SEQUENCE {
      capwapBaseMacAclId           Unsigned32,
      capwapBaseMacAclStationId    CapwapBaseStationIdTC,
      capwapBaseMacAclRowStatus    RowStatus
    }

capwapBaseMacAclId OBJECT-TYPE
    SYNTAX      Unsigned32
    MAX-ACCESS  not-accessible
    STATUS      current
    DESCRIPTION
        "Represents a unique id for a ACL."
    ::= { capwapBaseMacAclEntry 1 }

capwapBaseMacAclStationId OBJECT-TYPE
    SYNTAX      CapwapBaseStationIdTC
    MAX-ACCESS  read-create
    STATUS      current
    DESCRIPTION
        "Represents a station's MAC address which WTPs will no longer
         provides service to it."
    REFERENCE
        "Section 4.6.7. of CAPWAP Protocol Specification, RFC xxx."



::= { capwapBaseMacAclEntry 2 }

capwapBaseMacAclRowStatus OBJECT-TYPE
    SYNTAX      RowStatus
    MAX-ACCESS  read-create
    STATUS      current
    DESCRIPTION
        "This variable is used to create, modify, and/or delete a row
         in this table."
    ::= { capwapBaseMacAclEntry 3 }

-- End of capwapBaseMacAclTable table

-- End of AC Objects Group


-- WTP Objects Group

capwapBaseWtps OBJECT IDENTIFIER
    ::= { capwapBaseObjects 2 }

-- capwapBaseWtpStateTable table

capwapBaseWtpStateTable OBJECT-TYPE
    SYNTAX      SEQUENCE OF CapwapBaseWtpStateEntry
    MAX-ACCESS  not-accessible
    STATUS      current
    DESCRIPTION
        "A table of objects that display WTP CAPWAP FSM state."
    ::= { capwapBaseWtps 1 }

capwapBaseWtpStateEntry  OBJECT-TYPE
    SYNTAX      CapwapBaseWtpStateEntry
    MAX-ACCESS  not-accessible
    STATUS      current
    DESCRIPTION
        "A set of objects that display WTP CAPWAP FSM state."
    INDEX { capwapBaseWtpId }
    ::= { capwapBaseWtpStateTable 1 }

CapwapBaseWtpStateEntry ::= SEQUENCE {
      capwapBaseWtpId               CapwapBaseWtpIdTC,
      capwapBaseWtpIpAddressType    InetAddressType,
      capwapBaseWtpIpAddress        InetAddress,
      capwapBaseWtpPhyAddress       PhysAddress,
      capwapBaseWtpState            INTEGER
    }
capwapBaseWtpId OBJECT-TYPE
    SYNTAX      CapwapBaseWtpIdTC
    MAX-ACCESS  not-accessible
    STATUS      current
    DESCRIPTION
        "Represents the unique identifier of a WTP."
    ::= { capwapBaseWtpStateEntry 1 }

capwapBaseWtpIpAddressType OBJECT-TYPE
    SYNTAX      InetAddressType
    MAX-ACCESS  read-only
    STATUS      current
    DESCRIPTION
        "Represents the type of IP address of a WTP."
    ::= { capwapBaseWtpStateEntry 2 }

capwapBaseWtpIpAddress OBJECT-TYPE
    SYNTAX      InetAddress
    MAX-ACCESS  read-only
    STATUS      current
    DESCRIPTION
        "Represents the IP address of a WTP."
    ::= { capwapBaseWtpStateEntry 3 }

capwapBaseWtpPhyAddress OBJECT-TYPE
    SYNTAX      PhysAddress
    MAX-ACCESS  read-only
    STATUS      current
    DESCRIPTION
        "Represents the PHY address of a WTP."
    ::= { capwapBaseWtpStateEntry 4 }

capwapBaseWtpState  OBJECT-TYPE
    SYNTAX      INTEGER {
                  dtls(1),
                  join(2),
                  image(3),
                  configure(4),
                  dataCheck(5),
                  run(6),
                  clear(7),
                  unknown(8)
                }
    MAX-ACCESS  read-only
    STATUS      current
    DESCRIPTION
        "Represents the various possible CAPWAP FSM states of WTP
         The following enumerated values are supported:
dtls(1)      - DTLS negotiation states, which include
                          DTLS Setup, Authorize, DTLS Connect.
           join(2)      - WTP is joining with AC,
           image(3)     - WTP is downloading software,
           configure(4) - WTP is getting configuration from AC,
           dataCheck(5) - AC is waiting for the Data Channel Keep
                          Alive Packet.
           run(6)       - WTP comes to run state,
           clear(7)     - WTP recoveries default configuration.
           unknown(8)   - Operator already prepare configuration
                          for WTP, while WTP has not contact with AC
                          till now."
    REFERENCE
        "Section 2.3.1. of CAPWAP Protocol Specification, RFC xxx."
    ::= { capwapBaseWtpStateEntry 5 }

-- End of capwapBaseWtpStateTable Table


-- capwapBaseWtpTable Table

capwapBaseWtpTable OBJECT-TYPE
    SYNTAX      SEQUENCE OF CapwapBaseWtpEntry
    MAX-ACCESS  not-accessible
    STATUS      current
    DESCRIPTION
        "A table of objects that display and control WTPs in
         running state. Values of all read-write objects in this
         table are persistent at restart/reboot."
    ::= { capwapBaseWtps 2 }

capwapBaseWtpEntry  OBJECT-TYPE
    SYNTAX      CapwapBaseWtpEntry
    MAX-ACCESS  not-accessible
    STATUS      current
    DESCRIPTION
        "A set of objects that display and control a WTP in
         running state."
    INDEX { capwapBaseWtpCurrId }
    ::= { capwapBaseWtpTable 1 }

CapwapBaseWtpEntry ::= SEQUENCE {
      capwapBaseWtpCurrId                       CapwapBaseWtpIdTC,
      capwapBaseWtpPhyIndex                     PhysicalIndex,
      capwapBaseWtpName                         SnmpAdminString,
      capwapBaseWtpLocation                     SnmpAdminString,
      capwapBaseWtpBaseMacAddress               PhysAddress,
      capwapBaseTunnelModeOptions               CapwapBaseTunnelModeTC,

capwapBaseMacTypeOptions                  CapwapBaseMacTypeTC,
      capwapBaseWtpDiscoveryType                INTEGER,
      capwapBaseWtpRadiosInUseNum               Unsigned32,
      capwapBaseWtpRadioNumLimit                Unsigned32,
      capwapBaseWtpStaticIpEnable               TruthValue,
      capwapBaseWtpStaticIpType                 InetAddressType,
      capwapBaseWtpStaticIp                     InetAddress,
      capwapBaseWtpNetmask                      InetAddress,
      capwapBaseWtpGateway                      InetAddress,
      capwapBaseWtpFallbackEnable               INTEGER,
      capwapBaseWtpRetransmitCount              Unsigned32,
      capwapBaseWtpMaxDiscoveries               Unsigned32,
      capwapBaseWtpMaxFailedDTLSSessionRetry    Unsigned32,
      capwapBaseWtpMaxRetransmitCnt             Unsigned32,
      capwapBaseWtpDataChannelKeepAliveTimer    Unsigned32,
      capwapBaseWtpDataChannelDeadInterval      Unsigned32,
      capwapBaseWtpDiscoveryInterval            Unsigned32,
      capwapBaseWtpDTLSSessionDeleteTimer       Unsigned32,
      capwapBaseWtpEchoInterval                 Unsigned32,
      capwapBaseWtpIdleTimeout                  Unsigned32,
      capwapBaseWtpImageDataStartTimer          Unsigned32,
      capwapBaseWtpMaxDiscoveryInterval         Unsigned32,
      capwapBaseWtpReportInterval               Unsigned32,
      capwapBaseWtpRetransmitInterval           Unsigned32,
      capwapBaseWtpSilentInterval               Unsigned32,
      capwapBaseWtpStatisticsTimer              Unsigned32,
      capwapBaseWtpWaitDTLSTimer                Unsigned32
    }

capwapBaseWtpCurrId OBJECT-TYPE
    SYNTAX      CapwapBaseWtpIdTC
    MAX-ACCESS  not-accessible
    STATUS      current
    DESCRIPTION
        "Represents the unique identifier of a WTP Which is
         in running state."
    ::= { capwapBaseWtpEntry 1 }

capwapBaseWtpPhyIndex OBJECT-TYPE
    SYNTAX      PhysicalIndex
    MAX-ACCESS  read-only
    STATUS      current
    DESCRIPTION
        "Represents the unique physical index of a physical entity
         in the ENTITY-MIB. The information such as software version
         of specific WTP could be accessed through the index."
    ::= { capwapBaseWtpEntry 2 }
capwapBaseWtpName  OBJECT-TYPE
    SYNTAX      SnmpAdminString
    MAX-ACCESS  read-write
    STATUS      current
    DESCRIPTION
        "Represents the name of a WTP."
    REFERENCE
        "Section 4.6.44. of CAPWAP Protocol Specification, RFC xxx."
    ::= { capwapBaseWtpEntry 3 }

capwapBaseWtpLocation  OBJECT-TYPE
    SYNTAX      SnmpAdminString
    MAX-ACCESS  read-write
    STATUS      current
    DESCRIPTION
        "Represents the location of a WTP."
    REFERENCE
        "Section 4.6.29. of CAPWAP Protocol Specification, RFC xxx."
    ::= { capwapBaseWtpEntry 4 }

capwapBaseWtpBaseMacAddress  OBJECT-TYPE
    SYNTAX      PhysAddress
    MAX-ACCESS  read-only
    STATUS      current
    DESCRIPTION
        "Represents the WTP's Base MAC Address, which MAY be assigned
         to the primary Ethernet interface."
    REFERENCE
        "Section 4.6.39. of CAPWAP Protocol Specification, RFC xxx."
    ::= { capwapBaseWtpEntry 5 }

capwapBaseTunnelModeOptions  OBJECT-TYPE
    SYNTAX      CapwapBaseTunnelModeTC
    MAX-ACCESS  read-only
    STATUS      current
    DESCRIPTION
        "Represents the tunneling modes of operation supported by
         the WTP.
         The WTP MAY support more than one option, represented by the
         bit field below.
           localBridging(1) - Local Bridging Mode,
           dot3Tunnel(2)    - 802.3 Frame Tunnel Mode,
           nativeTunnel(3)  - Native Frame Tunnel Mode."
    REFERENCE
        "Section 4.6.42. of CAPWAP Protocol Specification, RFC xxx."
    ::= { capwapBaseWtpEntry 6 }

capwapBaseMacTypeOptions  OBJECT-TYPE



SYNTAX      CapwapBaseMacTypeTC
    MAX-ACCESS  read-only
    STATUS      current
    DESCRIPTION
        "Represents the MAC mode of operation supported by the WTP.
         The following enumerated values are supported:
           localMAC(0) - Local-MAC Mode,
           splitMAC(1) - Split-MAC Mode,
           both(2)     - Both Local-MAC Mode and Split-MAC Mode."
    REFERENCE
        "Section 4.6.43. of CAPWAP Protocol Specification, RFC xxx."
    ::= { capwapBaseWtpEntry 7 }

capwapBaseWtpDiscoveryType OBJECT-TYPE
    SYNTAX      INTEGER {
                  unknown(0),
                  staticConfig(1),
                  dhcp(2),
                  dns(3),
                  acRef(4)
                }
    MAX-ACCESS  read-only
    STATUS      current
    DESCRIPTION
        "Represents how WTP discovers the AC.
         The following enumerated values are supported:
           unknown(0)      - Unknown,
           staticConfig(1) - Static Configuration,
           dhcp(2)         - DHCP,
           dns(3)          - DNS,
           acRef(4)        - AC Referral."
    REFERENCE
        "Section 4.6.21. of CAPWAP Protocol Specification, RFC xxx."
    ::= { capwapBaseWtpEntry 8 }

capwapBaseWtpRadiosInUseNum OBJECT-TYPE
    SYNTAX      Unsigned32 (0..255)
    MAX-ACCESS  read-only
    STATUS      current
    DESCRIPTION
        "Represents the number of radios in use in the WTP."
    REFERENCE
        "Section 4.6.40. of CAPWAP Protocol Specification, RFC xxx."
    ::= { capwapBaseWtpEntry 9 }

capwapBaseWtpRadioNumLimit OBJECT-TYPE
    SYNTAX      Unsigned32 (0..255)
    MAX-ACCESS  read-only
STATUS      current
    DESCRIPTION
        "Represents the maximum radio number supported by the WTP."
    REFERENCE
        "Section 4.6.40. of CAPWAP Protocol Specification, RFC xxx."
    ::= { capwapBaseWtpEntry 10 }

capwapBaseWtpStaticIpEnable OBJECT-TYPE
    SYNTAX      TruthValue
    MAX-ACCESS  read-write
    STATUS      current
    DESCRIPTION
        "Represents whether the WTP should use a static IP address
         or not. A value of false disables the static IP address,
         while a value of true enables it."
    REFERENCE
        "Section 4.6.47. of CAPWAP Protocol Specification, RFC xxx."
    ::= { capwapBaseWtpEntry 11 }

capwapBaseWtpStaticIpType OBJECT-TYPE
    SYNTAX      InetAddressType
    MAX-ACCESS  read-write
    STATUS      current
    DESCRIPTION
        "Represents whether WTP uses IPV4 or IPV6 static IP address."
    ::= { capwapBaseWtpEntry 12 }

capwapBaseWtpStaticIp OBJECT-TYPE
    SYNTAX      InetAddress
    MAX-ACCESS  read-write
    STATUS      current
    DESCRIPTION
        "When capwapBaseWtpStaticIpEnable is true, it represents the
         static IP address to assign to the WTP."
    REFERENCE
        "Section 4.6.47. of CAPWAP Protocol Specification, RFC xxx."
    ::= { capwapBaseWtpEntry 13 }

capwapBaseWtpNetmask OBJECT-TYPE
    SYNTAX      InetAddress
    MAX-ACCESS  read-write
    STATUS      current
    DESCRIPTION
        "When capwapBaseWtpStaticIpEnable is true, it represents the
         netmask to assign to the WTP."
    REFERENCE
        "Section 4.6.47. of CAPWAP Protocol Specification, RFC xxx."
    ::= { capwapBaseWtpEntry 14 }
capwapBaseWtpGateway OBJECT-TYPE
    SYNTAX      InetAddress
    MAX-ACCESS  read-write
    STATUS      current
    DESCRIPTION
        "When capwapBaseWtpStaticIpEnable is true, it represents the
         gateway to assign to the WTP."
    REFERENCE
        "Section 4.6.47. of CAPWAP Protocol Specification, RFC xxx."
    ::= { capwapBaseWtpEntry 15 }

capwapBaseWtpFallbackEnable OBJECT-TYPE
    SYNTAX      INTEGER {
                  reserved(0),
                  enabled(1),
                  disabled(2)
                }
    MAX-ACCESS  read-write
    STATUS      current
    DESCRIPTION
        "Represents whether to enable or disable automatic CAPWAP
         fallback in the event that a WTP detects its preferred AC, and
         is not currently connected to it.
         The following enumerated values are supported:
           reserved(0) - The value is reserved,
           enabled(1)  - The fallback mode is enabled,
           disabled(2) - The fallback mode is disabled."
    REFERENCE
        "Section 4.6.41. of CAPWAP Protocol Specification, RFC xxx."
     ::= { capwapBaseWtpEntry 16 }

capwapBaseWtpRetransmitCount OBJECT-TYPE
    SYNTAX      Unsigned32
    MAX-ACCESS  read-only
    STATUS      current
    DESCRIPTION
        "Represents the number of retransmissions for a given
         CAPWAP packet."
    REFERENCE
        "Section 4.8.8. of CAPWAP Protocol Specification, RFC xxx."
    ::= { capwapBaseWtpEntry 17 }

capwapBaseWtpMaxDiscoveries OBJECT-TYPE
    SYNTAX      Unsigned32
    MAX-ACCESS  read-only
    STATUS      current
    DESCRIPTION
        "Represent the maximum number of Discovery Request messages
  that will be sent after a WTP boots."
    REFERENCE
        "Section 4.8.5. of CAPWAP Protocol Specification, RFC xxx."
    DEFVAL { 10 }
    ::= { capwapBaseWtpEntry 18 }

capwapBaseWtpMaxFailedDTLSSessionRetry OBJECT-TYPE
    SYNTAX      Unsigned32
    MAX-ACCESS  read-only
    STATUS      current
    DESCRIPTION
        "Represent the maximum number of failed DTLS session
         establishment attempts before the CAPWAP device enters a
         silent period."
    REFERENCE
        "Section 4.8.6. of CAPWAP Protocol Specification, RFC xxx."
    DEFVAL { 3 }
    ::= { capwapBaseWtpEntry 19 }

capwapBaseWtpMaxRetransmitCnt OBJECT-TYPE
    SYNTAX      Unsigned32
    MAX-ACCESS  read-only
    STATUS      current
    DESCRIPTION
        "Represent the maximum number of retransmission for a given
         CAPWAP packet before the link layer considers the peer dead."
    REFERENCE
        "Section 4.8.7. of CAPWAP Protocol Specification, RFC xxx."
    DEFVAL { 5 }
    ::= { capwapBaseWtpEntry 20 }

capwapBaseWtpDataChannelKeepAliveTimer OBJECT-TYPE
    SYNTAX      Unsigned32
    UNITS       "second"
    MAX-ACCESS  read-only
    STATUS      current
    DESCRIPTION
        "Represents the the next opportunity, in seconds, the WTP must
         transmit the Data Channel KeepAlive message."
    REFERENCE
        "Section 4.7.2. of CAPWAP Protocol Specification, RFC xxx."
    DEFVAL { 30 }
    ::= { capwapBaseWtpEntry 21 }

capwapBaseWtpDataChannelDeadInterval OBJECT-TYPE
    SYNTAX      Unsigned32
    UNITS       "second"
    MAX-ACCESS  read-only
STATUS      current
    DESCRIPTION
        "Represents the minimum time, in seconds, a WTP MUST wait
         without having received a Data Channel Keep Alive packet
         before the destination for the Data Channel Keep Alive
         packets may be considered dead."
    REFERENCE
        "Section 4.7.3. of CAPWAP Protocol Specification, RFC xxx."
    DEFVAL { 60 }
    ::= { capwapBaseWtpEntry 22 }

capwapBaseWtpDiscoveryInterval OBJECT-TYPE
    SYNTAX      Unsigned32
    UNITS       "second"
    MAX-ACCESS  read-only
    STATUS      current
    DESCRIPTION
        "Represents the minimum time, in seconds, that a WTP MUST
         wait after receiving a Discovery Response message, before
         initiating a DTLS handshake."
    REFERENCE
        "Section 4.7.5. of CAPWAP Protocol Specification, RFC xxx."
    DEFVAL { 5 }
    ::= { capwapBaseWtpEntry 23 }

capwapBaseWtpDTLSSessionDeleteTimer OBJECT-TYPE
    SYNTAX      Unsigned32
    UNITS       "second"
    MAX-ACCESS  read-only
    STATUS      current
    DESCRIPTION
        "Represents the minimum time, in seconds, a WTP MUST wait
         for DTLS session deletion."
    REFERENCE
        "Section 4.7.6. of CAPWAP Protocol Specification, RFC xxx."
    DEFVAL { 5 }
     ::= { capwapBaseWtpEntry 24 }

capwapBaseWtpEchoInterval OBJECT-TYPE
    SYNTAX      Unsigned32
    UNITS       "second"
    MAX-ACCESS  read-write
    STATUS      current
    DESCRIPTION
        "Represents the minimum time, in seconds, between sending Echo
         Request messages to the AC with which the WTP has joined."
    REFERENCE
        "Section 4.7.7. of CAPWAP Protocol Specification, RFC xxx."
DEFVAL { 30 }
    ::= { capwapBaseWtpEntry 25 }

capwapBaseWtpIdleTimeout OBJECT-TYPE
    SYNTAX      Unsigned32
    UNITS       "second"
    MAX-ACCESS  read-write
    STATUS      current
    DESCRIPTION
        "Represents the idle timeout value that the WTP SHOULD enforce
         for its active stations."
    REFERENCE
        "Section 4.7.8. of CAPWAP Protocol Specification, RFC xxx."
    DEFVAL { 300 }
    ::= { capwapBaseWtpEntry 26 }

capwapBaseWtpImageDataStartTimer OBJECT-TYPE
    SYNTAX      Unsigned32
    UNITS       "second"
    MAX-ACCESS  read-only
    STATUS      current
    DESCRIPTION
        "Represents the number of seconds the WTP will wait for its peer
         to transmit the Image Data Request."
    REFERENCE
        "Section 4.7.9. of CAPWAP Protocol Specification, RFC xxx."
    DEFVAL { 30 }
    ::= { capwapBaseWtpEntry 27 }

capwapBaseWtpMaxDiscoveryInterval OBJECT-TYPE
    SYNTAX      Unsigned32
    UNITS       "second"
    MAX-ACCESS  read-write
    STATUS      current
    DESCRIPTION
        "Represents the maximum time allowed between sending Discovery
         Request messages, in seconds.  This value MUST be no less than
         2 seconds and no greater than 180 seconds."
    REFERENCE
        "Section 4.7.10. of CAPWAP Protocol Specification, RFC xxx."
    DEFVAL { 20 }
    ::= { capwapBaseWtpEntry 28 }

capwapBaseWtpReportInterval OBJECT-TYPE
    SYNTAX      Unsigned32
    UNITS       "second"
    MAX-ACCESS  read-write
    STATUS      current
DESCRIPTION
        "Represents the interval for WTP to send Decryption Error
         report."
    REFERENCE
        "Section 4.7.11. of CAPWAP Protocol Specification, RFC xxx."
    DEFVAL { 120 }
    ::= { capwapBaseWtpEntry 29 }

capwapBaseWtpRetransmitInterval OBJECT-TYPE
    SYNTAX      Unsigned32
    UNITS       "second"
    MAX-ACCESS  read-only
    STATUS      current
    DESCRIPTION
        "Represents the minimum time, in seconds, in which a
         non-acknowledged CAPWAP packet will be retransmitted."
    REFERENCE
        "Section 4.7.12. of CAPWAP Protocol Specification, RFC xxx."
    DEFVAL { 3 }
    ::= { capwapBaseWtpEntry 30 }

capwapBaseWtpSilentInterval OBJECT-TYPE
    SYNTAX      Unsigned32
    UNITS       "second"
    MAX-ACCESS  read-write
    STATUS      current
    DESCRIPTION
        "Represents the minimum time, in seconds, a WTP MUST wait
         before it MAY again send Discovery Request messages or attempt
         to a establish DTLS session."
    REFERENCE
        "Section 4.7.13. of CAPWAP Protocol Specification, RFC xxx."
    DEFVAL { 30 }
    ::= { capwapBaseWtpEntry 31 }

capwapBaseWtpStatisticsTimer OBJECT-TYPE
    SYNTAX      Unsigned32
    UNITS       "second"
    MAX-ACCESS  read-write
    STATUS      current
    DESCRIPTION
        "Represents the interval the WTP uses between the WTP Events
         Requests it transmits to the AC to communicate its statistics,
         in seconds."
    REFERENCE
        "Section 4.7.14. of CAPWAP Protocol Specification, RFC xxx."
    DEFVAL { 120 }
    ::= { capwapBaseWtpEntry 32 }
capwapBaseWtpWaitDTLSTimer OBJECT-TYPE
    SYNTAX      Unsigned32
    UNITS       "second"
    MAX-ACCESS  read-write
    STATUS      current
    DESCRIPTION
        "Represents the maximum time, in seconds, an AC MUST wait
         without having received a DTLS Handshake message from an AC.
         This timer MUST be greater than 30 seconds."
    REFERENCE
        "Section 4.7.15. of CAPWAP Protocol Specification, RFC xxx."
    DEFVAL { 60 }
    ::= { capwapBaseWtpEntry 33 }
-- End of capwapBaseWtpTable table


-- capwapBaseRadioBindTable Table

capwapBaseRadioBindTable OBJECT-TYPE
    SYNTAX      SEQUENCE OF CapwapBaseRadioBindEntry
    MAX-ACCESS  not-accessible
    STATUS      current
    DESCRIPTION
        "A table of objects that display the mapping relationship
         between specific interface of 'WTP Virtual Radio Interface'
         ifType and PHY radio. The mapping relationship in this table
         is persistent at restart/reboot."
    ::= { capwapBaseWtps 3 }

capwapBaseRadioBindEntry  OBJECT-TYPE
    SYNTAX      CapwapBaseRadioBindEntry
    MAX-ACCESS  not-accessible
    STATUS      current
    DESCRIPTION
        "A set of objects that display the mapping relationship
         between 'WTP Virtual Radio' and PHY radio."
    INDEX {
      capwapBaseWtpId,
      capwapBaseRadioId
    }
    ::= { capwapBaseRadioBindTable 1 }

CapwapBaseRadioBindEntry ::= SEQUENCE {
      capwapBaseRadioId                 CapwapBaseRadioIdTC,
      capwapBaseVirtualRadioIfIndex     InterfaceIndex,
      capwapBaseRadioWirelessBinding    INTEGER
    }



capwapBaseRadioId OBJECT-TYPE
    SYNTAX      CapwapBaseRadioIdTC
    MAX-ACCESS  not-accessible
    STATUS      current
    DESCRIPTION
        "Represents the identifier of a PHY radio on a WTP, and only
         requires unique on a WTP.
         For example, WTP A and WTP B will use same value of
         capwapBaseRadioId for their first radio."
    REFERENCE
        "Section 4.3. of CAPWAP Protocol Specification, RFC xxx."
    ::= { capwapBaseRadioBindEntry 1 }

capwapBaseVirtualRadioIfIndex OBJECT-TYPE
    SYNTAX      InterfaceIndex
    MAX-ACCESS  read-only
    STATUS      current
    DESCRIPTION
         "Represents the index value that uniquely identifies a
         'WLAN Virtual Radio Interface'. The interface identified by a
         particular value of this index is the same interface as
         identified by the same value of ifIndex.
         Before WTPs connect to AC and get configuration, operator
         will prepare configuration for them. On the AC, there are
         interfaces of 'WTP Virtual Radio Interface' ifType which
         represent PHY radio interfaces on the WTP.
         As most MIBs use ifIndex to identify an interface for
         configuration and statistic data, for example, IEEE 802.11 MIB.
         It will be very easy to reuse other MIBs such as IEEE 802.11
         MIB by 'WTP Virtual Radio Interface'."
    ::= { capwapBaseRadioBindEntry 2 }

capwapBaseRadioWirelessBinding OBJECT-TYPE
    SYNTAX      INTEGER {
                  reserved0(0),
                  dot11(1),
                  reserved2(2),
                  epc(3)
                }
    MAX-ACCESS  read-only
    STATUS      current
    DESCRIPTION
        "Represents the wireless binding type for radio.
         The following enumerated values are supported:
           reserved0(0) - Reserved,
           dot11(1)     - IEEE 802.11,
           reserved2(2) - Reserved,
           epc(3)       - EPCGlobal."
 REFERENCE
        "Section 4.3. of CAPWAP Protocol Specification, RFC xxx."
    ::= { capwapBaseRadioBindEntry 3 }

-- End of capwapBaseRadioBindTable Table


-- capwapBaseStationTable Table

capwapBaseStationTable OBJECT-TYPE
    SYNTAX      SEQUENCE OF CapwapBaseStationEntry
    MAX-ACCESS  not-accessible
    STATUS      current
    DESCRIPTION
        "A table of objects that display stations which are accessing
         the wireless service provided by the AC."
    ::= { capwapBaseWtps 4 }

capwapBaseStationEntry OBJECT-TYPE
    SYNTAX      CapwapBaseStationEntry
    MAX-ACCESS  not-accessible
    STATUS      current
    DESCRIPTION
        "A set of objects that display a station which is
         associated with the specific radio on the WTP."
    INDEX {
      capwapBaseWtpCurrId,
      capwapBaseRadioId,
      capwapBaseStationId
    }
    ::= { capwapBaseStationTable 1 }

CapwapBaseStationEntry ::= SEQUENCE {
      capwapBaseStationId           CapwapBaseStationIdTC,
      capwapBaseStationAddedTime    DateAndTime,
      capwapBaseStationVlanName     SnmpAdminString
    }

capwapBaseStationId OBJECT-TYPE
    SYNTAX      CapwapBaseStationIdTC
    MAX-ACCESS  not-accessible
    STATUS      current
    DESCRIPTION
        "Represents the unique identifier of the station."
    REFERENCE
        "Section 4.6.8. of CAPWAP Protocol Specification, RFC xxx."
    ::= { capwapBaseStationEntry 1 }
capwapBaseStationAddedTime OBJECT-TYPE
    SYNTAX      DateAndTime
    MAX-ACCESS  read-only
    STATUS      current
    DESCRIPTION
        "Represents the time when the station is added."
    REFERENCE
        "Section 4.6.8. of CAPWAP Protocol Specification, RFC xxx."
    ::= { capwapBaseStationEntry 2 }

capwapBaseStationVlanName OBJECT-TYPE
    SYNTAX      SnmpAdminString
    MAX-ACCESS  read-only
    STATUS      current
    DESCRIPTION
        "Represents VLAN name to which the station is associated."
    REFERENCE
        "Section 4.6.8. of CAPWAP Protocol Specification, RFC xxx."
    ::= { capwapBaseStationEntry 3 }

-- End of capwapBaseStationTable Table


--  capwapBaseWtpRebootStatTable

capwapBaseWtpRebootStatsTable  OBJECT-TYPE
    SYNTAX      SEQUENCE OF CapwapBaseWtpRebootStatsEntry
    MAX-ACCESS  not-accessible
    STATUS      current
    DESCRIPTION
        "A table of objects that display WTPs' reboot statistics."
    REFERENCE
        "Section 4.6.46. of CAPWAP Protocol Specification, RFC xxx."
    ::= { capwapBaseWtps 5 }

capwapBaseWtpRebootStatsEntry  OBJECT-TYPE
    SYNTAX      CapwapBaseWtpRebootStatsEntry
    MAX-ACCESS  not-accessible
    STATUS      current
    DESCRIPTION
        "A set of objects that display the reboot statistic data
         of a WTP."
    REFERENCE
        "Section 4.6.46. of CAPWAP Protocol Specification, RFC xxx."
    INDEX { capwapBaseWtpCurrId }
    ::= { capwapBaseWtpRebootStatsTable 1 }

CapwapBaseWtpRebootStatsEntry ::= SEQUENCE {



capwapBaseWtpRebootCount            Counter32,
      capwapBaseWtpInitCount              Counter32,
      capwapBaseWtpLinkFailureCount       Counter32,
      capwapBaseWtpSwFailureCount         Counter32,
      capwapBaseWtpHwFailureCount         Counter32,
      capwapBaseWtpOtherFailureCount      Counter32,
      capwapBaseWtpUnknownFailureCount    Counter32,
      capwapBaseWtpLastFailureType        INTEGER
    }

capwapBaseWtpRebootCount OBJECT-TYPE
    SYNTAX      Counter32
    MAX-ACCESS  read-only
    STATUS      current
    DESCRIPTION
        "Represents the number of reboots that have occurred due to a
         WTP crash.  A value of 65535 implies that this information is
         not available on the WTP."
    REFERENCE
        "Section 4.6.46. of CAPWAP Protocol Specification, RFC xxx."
    ::= { capwapBaseWtpRebootStatsEntry 1 }

capwapBaseWtpInitCount OBJECT-TYPE
    SYNTAX      Counter32
    MAX-ACCESS  read-only
    STATUS      current
    DESCRIPTION
        "Represents the number of reboots that have occurred at the
         request of a CAPWAP protocol message, such as a change in
         configuration that required a reboot or an explicit CAPWAP
         protocol reset request.  A value of 65535 implies that this
         information is not available on the WTP."
    REFERENCE
        "Section 4.6.46. of CAPWAP Protocol Specification, RFC xxx."
    ::= { capwapBaseWtpRebootStatsEntry 2 }

capwapBaseWtpLinkFailureCount OBJECT-TYPE
    SYNTAX      Counter32
    MAX-ACCESS  read-only
    STATUS      current
    DESCRIPTION
        "Represents the number of times that a CAPWAP protocol
         connection with an AC has failed due to link failure."
    REFERENCE
        "Section 4.6.46. of CAPWAP Protocol Specification, RFC xxx."
    ::= { capwapBaseWtpRebootStatsEntry 3 }

capwapBaseWtpSwFailureCount OBJECT-TYPE
SYNTAX      Counter32
    MAX-ACCESS  read-only
    STATUS      current
    DESCRIPTION
        "Represents the number of times that a CAPWAP protocol
         connection with an AC has failed due to software related
         reasons."
    REFERENCE
        "Section 4.6.46. of CAPWAP Protocol Specification, RFC xxx."
    ::= { capwapBaseWtpRebootStatsEntry 4 }

capwapBaseWtpHwFailureCount OBJECT-TYPE
    SYNTAX      Counter32
    MAX-ACCESS  read-only
    STATUS      current
    DESCRIPTION
        "Represents the number of times that a CAPWAP protocol
         connection with an AC has failed due to hardware related
         reasons."
    REFERENCE
        "Section 4.6.46. of CAPWAP Protocol Specification, RFC xxx."
    ::= { capwapBaseWtpRebootStatsEntry 5 }

capwapBaseWtpOtherFailureCount OBJECT-TYPE
    SYNTAX      Counter32
    MAX-ACCESS  read-only
    STATUS      current
    DESCRIPTION
        "Represents the number of times that a CAPWAP protocol
         connection with an AC has failed due to known reasons, other
         than AC initiated, link, software or hardware failure."
    REFERENCE
        "Section 4.6.46. of CAPWAP Protocol Specification, RFC xxx."
    ::= { capwapBaseWtpRebootStatsEntry 6 }

capwapBaseWtpUnknownFailureCount OBJECT-TYPE
    SYNTAX      Counter32
    MAX-ACCESS  read-only
    STATUS      current
    DESCRIPTION
        "Represents the number of times that a CAPWAP protocol
         connection with an AC has failed for unknown reasons."
    REFERENCE
        "Section 4.6.46. of CAPWAP Protocol Specification, RFC xxx."
    ::= { capwapBaseWtpRebootStatsEntry 7 }

capwapBaseWtpLastFailureType OBJECT-TYPE
    SYNTAX      INTEGER {
 notSupport(0),
                  acInit(1),
                  linkFailure(2),
                  swFailure(3),
                  hwFailure(4),
                  otherFailure(5),
                  unknown(255)
                }
    MAX-ACCESS  read-only
    STATUS      current
    DESCRIPTION
        "Represents the failure type of the most recent WTP failure.
         The following enumerated values are supported:
           notSupport(0)   - Not Supported,
           acInit(1)       - AC Initiated,
           linkFailure(2)  - Link Failure,
           swFailure(3)    - Software Failure,
           hwFailure(4)    - Hardware Failure,
           otherFailure(5) - Other Failure,
           unknown(255)    - Unknown (e.g., WTP doesn't keep track
                             of info)."
    REFERENCE
        "Section 4.6.46. of CAPWAP Protocol Specification, RFC xxx."
    ::= { capwapBaseWtpRebootStatsEntry 8 }

--  End of capwapBaseWtpRebootStatsTable table


--  capwapBaseRadioStatsTable table

capwapBaseRadioStatsTable  OBJECT-TYPE
    SYNTAX      SEQUENCE OF CapwapBaseRadioStatsEntry
    MAX-ACCESS  not-accessible
    STATUS      current
    DESCRIPTION
        "A table of objects that display statistics on radios behavior,
         and reasons why the WTP radio has been reset."
    REFERENCE
        "Section 4.6.45. of CAPWAP Protocol Specification, RFC xxx."
    ::= { capwapBaseWtps 6 }

capwapBaseRadioStatsEntry  OBJECT-TYPE
    SYNTAX      CapwapBaseRadioStatsEntry
    MAX-ACCESS  not-accessible
    STATUS      current
    DESCRIPTION
        "A set of objects that display the statistic data of
         events happened on a specific radio of a WTP."

INDEX { capwapBaseWtpCurrId, capwapBaseRadioId }
    ::= { capwapBaseRadioStatsTable 1 }

CapwapBaseRadioStatsEntry ::= SEQUENCE {
      capwapBaseRadioResetCount            Counter32,
      capwapBaseRadioSwFailCount           Counter32,
      capwapBaseRadioHwFailCount           Counter32,
      capwapBaseRadioOtherFailCount        Counter32,
      capwapBaseRadioUnknownFailCount      Counter32,
      capwapBaseRadioConfigUpdateCount     Counter32,
      capwapBaseRadioChannelChangeCount    Counter32,
      capwapBaseRadioBandChangeCount       Counter32,
      capwapBaseRadioCurrentNoiseFloor     Integer32,
      capwapBaseRadioDecryptErrorCount     Counter32,
      capwapBaseRadioLastFailType          INTEGER
    }

capwapBaseRadioResetCount OBJECT-TYPE
    SYNTAX      Counter32
    MAX-ACCESS  read-only
    STATUS      current
    DESCRIPTION
        "Represents the number of times that that the radio has been
         reset."
    REFERENCE
        "Section 4.6.45. of CAPWAP Protocol Specification, RFC xxx."
    ::= { capwapBaseRadioStatsEntry 1 }

capwapBaseRadioSwFailCount OBJECT-TYPE
    SYNTAX      Counter32
    MAX-ACCESS  read-only
    STATUS      current
    DESCRIPTION
        "Represents the number of times that the radio has failed due
         to software related reasons."
    REFERENCE
        "Section 4.6.45. of CAPWAP Protocol Specification, RFC xxx."
    ::= { capwapBaseRadioStatsEntry 2 }

capwapBaseRadioHwFailCount OBJECT-TYPE
    SYNTAX      Counter32
    MAX-ACCESS  read-only
    STATUS      current
    DESCRIPTION
        "Represents the number of times that the radio has failed due
         to hardware related reasons."
    REFERENCE
        "Section 4.6.45. of CAPWAP Protocol Specification, RFC xxx."

::= { capwapBaseRadioStatsEntry 3 }

capwapBaseRadioOtherFailCount OBJECT-TYPE
    SYNTAX      Counter32
    MAX-ACCESS  read-only
    STATUS      current
    DESCRIPTION
        "Represents the number of times that the radio has failed due to
         known reasons, other than software or hardware failure."
    REFERENCE
        "Section 4.6.45. of CAPWAP Protocol Specification, RFC xxx."
    ::= { capwapBaseRadioStatsEntry 4 }

capwapBaseRadioUnknownFailCount OBJECT-TYPE
    SYNTAX      Counter32
    MAX-ACCESS  read-only
    STATUS      current
    DESCRIPTION
        "Represents the number of times that the radio has failed for
         unknown reasons."
    REFERENCE
        "Section 4.6.45. of CAPWAP Protocol Specification, RFC xxx."
    ::= { capwapBaseRadioStatsEntry 5 }

capwapBaseRadioConfigUpdateCount OBJECT-TYPE
    SYNTAX      Counter32
    MAX-ACCESS  read-only
    STATUS      current
    DESCRIPTION
        "Represents the number of times that the radio configuration has
         been updated."
    REFERENCE
        "Section 4.6.45. of CAPWAP Protocol Specification, RFC xxx."
    ::= { capwapBaseRadioStatsEntry 6 }

capwapBaseRadioChannelChangeCount OBJECT-TYPE
    SYNTAX      Counter32
    MAX-ACCESS  read-only
    STATUS      current
    DESCRIPTION
        "Represents the number of times that the radio channel has
         been changed."
    REFERENCE
        "Section 4.6.45. of CAPWAP Protocol Specification, RFC xxx."
    ::= { capwapBaseRadioStatsEntry 7 }

capwapBaseRadioBandChangeCount OBJECT-TYPE
    SYNTAX      Counter32
MAX-ACCESS  read-only
    STATUS      current
    DESCRIPTION
        "Represents the number of times that the radio has changed
         frequency bands."
    REFERENCE
        "Section 4.6.45. of CAPWAP Protocol Specification, RFC xxx."
    ::= { capwapBaseRadioStatsEntry 8 }

capwapBaseRadioCurrentNoiseFloor OBJECT-TYPE
    SYNTAX      Integer32
    UNITS       "dBm"
    MAX-ACCESS  read-only
    STATUS      current
    DESCRIPTION
        "Represents the noise floor of the radio receiver in units of
         dBm."
    REFERENCE
        "Section 4.6.45. of CAPWAP Protocol Specification, RFC xxx."
    ::= { capwapBaseRadioStatsEntry 9 }

capwapBaseRadioDecryptErrorCount OBJECT-TYPE
    SYNTAX      Counter32
    MAX-ACCESS  read-only
    STATUS      current
    DESCRIPTION
        "Represents the number of decryption errors that occurred on the
         WTP.  Note that this field is only valid in cases where the WTP
         provides encryption/decryption services."
    REFERENCE
        "Section 4.6.45. of CAPWAP Protocol Specification, RFC xxx."
    ::= { capwapBaseRadioStatsEntry 10 }

capwapBaseRadioLastFailType OBJECT-TYPE
    SYNTAX      INTEGER {
                  notSupport(0),
                  swFailure(1),
                  hwFailure(2),
                  otherFailure(3),
                  unknown(255)
                }
    MAX-ACCESS  read-only
    STATUS      current
    DESCRIPTION
        "Represents the failure type of the most recent radio failure.
         The following enumerated values are supported:
           notSupport(0)   - Not Supported,
           swFailure(1)    - Software Failure,
 hwFailure(2)    - Hardware Failure,
           otherFailure(3) - Other Failure,
           unknown(255)    - Unknown."
    REFERENCE
        "Section 4.6.45. of CAPWAP Protocol Specification, RFC xxx."
    ::= { capwapBaseRadioStatsEntry 11 }

--  End of capwapBaseRadioStatsTable table
-- End of WTP Objects Group


-- CAPWAP Base Parameters Group

capwapBaseParameters OBJECT IDENTIFIER
    ::= { capwapBaseObjects 3 }

capwapBaseAcMaxRetransmitCnt OBJECT-TYPE
    SYNTAX      Unsigned32
    MAX-ACCESS  read-write
    STATUS      current
    DESCRIPTION
        "Represent the maximum number of retransmission for a given
         CAPWAP packet before the link layer considers the peer dead."
    REFERENCE
        "Section 4.8.7. of CAPWAP Protocol Specification, RFC xxx."
    DEFVAL { 5 }
    ::= { capwapBaseParameters 1 }

capwapBaseAcChangeStatePendingTimer OBJECT-TYPE
    SYNTAX      Unsigned32
    UNITS       "second"
    MAX-ACCESS  read-write
    STATUS      current
    DESCRIPTION
        "Represents the maximum time, in seconds, the AC will wait
         for the Change State Event Request from the WTP after having
         transmitted a successful Configuration Status Response
         message."
    REFERENCE
        "Section 4.7.1. of CAPWAP Protocol Specification, RFC xxx."
    DEFVAL { 25 }
    ::= { capwapBaseParameters 2 }

capwapBaseAcDataCheckTimer OBJECT-TYPE
    SYNTAX      Unsigned32
    UNITS       "second"
    MAX-ACCESS  read-write
    STATUS      current


DESCRIPTION
        "Represents The number of seconds the AC will wait for
         the Data Channel Keep Alive, which is required by the
         CAPWAP state machine's Data Check state.
         The AC resets the state machine if this timer expires
         prior to transitioning to the next state."
    REFERENCE
        "Section 4.7.4. of CAPWAP Protocol Specification, RFC xxx."
    DEFVAL { 30 }
    ::= { capwapBaseParameters 3 }

capwapBaseAcDTLSSessionDeleteTimer OBJECT-TYPE
    SYNTAX      Unsigned32
    UNITS       "second"
    MAX-ACCESS  read-write
    STATUS      current
    DESCRIPTION
        "Represents the minimum time, in seconds, an AC MUST wait
         for DTLS session deletion."
    REFERENCE
        "Section 4.7.6. of CAPWAP Protocol Specification, RFC xxx."
    DEFVAL { 5 }
    ::= { capwapBaseParameters 4 }

capwapBaseAcEchoInterval OBJECT-TYPE
    SYNTAX      Unsigned32
    UNITS       "second"
    MAX-ACCESS  read-write
    STATUS      current
    DESCRIPTION
        "Represents the minimum time, in seconds, between sending Echo
         Request messages to the AC with which the WTP has joined."
    REFERENCE
        "Section 4.7.7. of CAPWAP Protocol Specification, RFC xxx."
    DEFVAL { 30 }
    ::= { capwapBaseParameters 5 }

capwapBaseAcRetransmitInterval OBJECT-TYPE
    SYNTAX      Unsigned32
    UNITS       "second"
    MAX-ACCESS  read-write
    STATUS      current
    DESCRIPTION
        "Represents the minimum time, in seconds, in which a
         non-acknowledged CAPWAP packet will be retransmitted."
    REFERENCE
        "Section 4.7.12. of CAPWAP Protocol Specification, RFC xxx."
    DEFVAL { 3 }
::= { capwapBaseParameters 6 }

capwapBaseAcSilentInterval OBJECT-TYPE
    SYNTAX      Unsigned32
    UNITS       "second"
    MAX-ACCESS  read-write
    STATUS      current
    DESCRIPTION
        "Represents the minimum time, in seconds, during which the AC
         SHOULD ignore all CAPWAP and DTLS packets received from the
         WTP that is in the Sulking state."
    REFERENCE
        "Section 4.7.13. of CAPWAP Protocol Specification, RFC xxx."
    DEFVAL { 30 }
    ::= { capwapBaseParameters 7 }

capwapBaseAcWaitDTLSTimer OBJECT-TYPE
    SYNTAX      Unsigned32
    UNITS       "second"
    MAX-ACCESS  read-write
    STATUS      current
    DESCRIPTION
        "Represents the maximum time, in seconds, an AC MUST wait
         without having received a DTLS Handshake message from an AC.
         This timer MUST be greater than 30 seconds."
    REFERENCE
        "Section 4.7.15. of CAPWAP Protocol Specification, RFC xxx."
    DEFVAL { 60 }
    ::= { capwapBaseParameters 8 }

capwapBaseAcWaitJoinTimer OBJECT-TYPE
    SYNTAX      Unsigned32
    UNITS       "second"
    MAX-ACCESS  read-write
    STATUS      current
    DESCRIPTION
        "Represents the maximum time, in seconds, an AC will wait after
         the DTLS session has been established until it receives the
         Join Request from the WTP. This timer MUST be greater than 20
         seconds."
    REFERENCE
        "Section 4.7.16. of CAPWAP Protocol Specification, RFC xxx."
    DEFVAL { 60 }
    ::= { capwapBaseParameters 9 }

-- End of CAPWAP Base Parameters Group
-- CAPWAP Statistics Group

capwapBaseStats OBJECT IDENTIFIER
    ::= { capwapBaseObjects 4 }

capwapBaseFailedDTLSAuthFailCount OBJECT-TYPE
    SYNTAX      Counter32
    MAX-ACCESS  read-only
    STATUS      current
    DESCRIPTION
        "Represents the number of failed DTLS session
         establishment attempts due to authentication failures."
    REFERENCE
        "Section 4.8.3. of CAPWAP Protocol Specification, RFC xxx."
    ::= { capwapBaseStats 1 }

capwapBaseFailedDTLSSessionCount OBJECT-TYPE
    SYNTAX      Counter32
    MAX-ACCESS  read-only
    STATUS      current
    DESCRIPTION
        "Represents the number of failed DTLS session
         establishment attempts."
    REFERENCE
        "Section 4.8.4. of CAPWAP Protocol Specification, RFC xxx."
    ::= { capwapBaseStats 2 }

-- Notifications

capwapBaseChannelUp NOTIFICATION-TYPE
    OBJECTS     {
                  capwapBaseNtfWtpId,
                  capwapBaseNtfChannelType,
                  capwapBaseNtfAuthenMethod
                }
    STATUS      current
    DESCRIPTION
        "This notification is sent by AC when a CAPWAP channel
         established. The notification is separated for data or control
         channel."
    ::= { capwapBaseNotifications 1 }

capwapBaseChannelDown NOTIFICATION-TYPE
    OBJECTS     {
                  capwapBaseNtfWtpId,
                  capwapBaseNtfChannelType,
                  capwapBaseNtfChannelDownReason
                }
STATUS      current
    DESCRIPTION
        "This notification is sent by AC when CAPWAP channel becomes
         down. The notification is separated for data or control
         channel."
    ::= { capwapBaseNotifications 2 }

capwapBaseDecryptErrorReport NOTIFICATION-TYPE
    OBJECTS     {
                  capwapBaseNtfWtpId,
                  capwapBaseNtfRadioId,
                  capwapBaseNtfStationIdList
                }
    STATUS      current
    DESCRIPTION
        "This notification is generated when a WTP that has occurred
         decryption error since the last report."
    REFERENCE
        "Section 4.6.17. of CAPWAP Protocol Specification, RFC xxx."
    ::= { capwapBaseNotifications 3 }

capwapBaseJoinFailure NOTIFICATION-TYPE
    OBJECTS     {
                  capwapBaseNtfWtpId,
                  capwapBaseNtfJoinFailureReason
                }
    STATUS      current
    DESCRIPTION
        "This notification is generated when a WTP fails to join."
    REFERENCE
        "Section 4.6.34. of CAPWAP Protocol Specification, RFC xxx."
    ::= { capwapBaseNotifications 4 }

capwapBaseImageUpgradeFailure NOTIFICATION-TYPE
    OBJECTS     {
                  capwapBaseNtfWtpId,
                  capwapBaseNtfImageFailureReason
                }
    STATUS      current
    DESCRIPTION
        "This notification is generated when a WTP fails to update
         firmware image."
    REFERENCE
        "Section 4.6.34. of CAPWAP Protocol Specification, RFC xxx."
    ::= { capwapBaseNotifications 5 }

capwapBaseConfigMsgError NOTIFICATION-TYPE
    OBJECTS     {

capwapBaseNtfWtpId,
                  capwapBaseNtfConfigMsgErrorType,
                  capwapBaseNtfMsgErrorElements
                }
    STATUS      current
    DESCRIPTION
        "This notification is generated when a WTP received message
         elements in the configuration management messages which it was
         unable to apply locally."
    REFERENCE
        "Section 4.6.34. of CAPWAP Protocol Specification, RFC xxx."
    ::= { capwapBaseNotifications 6 }

capwapBaseRadioOperableStatus NOTIFICATION-TYPE
    OBJECTS     {
                  capwapBaseNtfWtpId,
                  capwapBaseNtfRadioId,
                  capwapBaseNtfRadioOperStatusFlag,
                  capwapBaseNtfRadioStatusCause
                }
    STATUS      current
    DESCRIPTION
        "The notification is generated when a radio's operational state
         is changed."
    REFERENCE
        "Section 4.6.33. of CAPWAP Protocol Specification, RFC xxx."
    ::= { capwapBaseNotifications 7 }

capwapBaseAuthenticationFailure NOTIFICATION-TYPE
    OBJECTS     {
                  capwapBaseNtfWtpId,
                  capwapBaseNtfChannelType,
                  capwapBaseNtfAuthenMethod,
                  capwapBaseNtfAuthenFailureReason
                }
    STATUS      current
    DESCRIPTION
        "The notification will notify the authentication failure event,
         and provides the reason for it."
    ::= { capwapBaseNotifications 8 }

-- Objects used only in notifications


-- for notifications
capwapBaseNotifyVarObjects OBJECT IDENTIFIER
    ::= { capwapBaseObjects 5 }
capwapBaseNtfWtpId OBJECT-TYPE
    SYNTAX      CapwapBaseWtpIdTC
    MAX-ACCESS  accessible-for-notify
    STATUS      current
    DESCRIPTION
        "Represents the unique identifier of a WTP."
    ::= { capwapBaseNotifyVarObjects 1 }

capwapBaseNtfRadioId OBJECT-TYPE
    SYNTAX      CapwapBaseRadioIdTC
    MAX-ACCESS  accessible-for-notify
    STATUS      current
    DESCRIPTION
        "Represents the identifier of a PHY radio on a WTP, and only
         requires unique on a WTP.
         For example, WTP A and WTP B will use same value of
         capwapBaseNtfRadioId for their first radio."
    REFERENCE
        "Section 4.3. of CAPWAP Protocol Specification, RFC xxx."
    ::= { capwapBaseNotifyVarObjects 2 }

capwapBaseNtfChannelType OBJECT-TYPE
    SYNTAX      CapwapBaseChannelTypeTC
    MAX-ACCESS  accessible-for-notify
    STATUS      current
    DESCRIPTION
        "Represents the channel type for CAPWAP protocol."
    ::= { capwapBaseNotifyVarObjects 3 }

capwapBaseNtfAuthenMethod OBJECT-TYPE
    SYNTAX      CapwapBaseAuthenMethodTC
    MAX-ACCESS  accessible-for-notify
    STATUS      current
    DESCRIPTION
        "Represents authentication method for Channel."
    ::= { capwapBaseNotifyVarObjects 4 }

capwapBaseNtfChannelDownReason OBJECT-TYPE
    SYNTAX      INTEGER {
                  timeout(1),
                  rekeyfailure(2),
                  acRebootWtp(3),
                  dtlsError(4),
                  maxRetransmit(5)
                }
    MAX-ACCESS  accessible-for-notify
    STATUS      current
    DESCRIPTION
 "Represents the reason for Channel down.
         The following enumerated values are supported:
           timeout(1)       - The keep alive is timeout,
           rekeyfailure(2)  - Rekey process is failed, channel will be
                              broken.
           acRebootWtp(3)   - AC reboot WTP.
           dtlsError(4)     - DTLS notifications: DTLSAborted,
                              DTLSReassemblyFailure, DTLSPeerDisconnect,
                              or frequent DTLSDecapFailure.
           maxRetransmit(5) - The underlying reliable transport's
                              RetransmitCount counter has reached the
                              MaxRetransmit variable"
    ::= { capwapBaseNotifyVarObjects 5 }

capwapBaseNtfStationIdList OBJECT-TYPE
    SYNTAX      OCTET STRING
    MAX-ACCESS  accessible-for-notify
    STATUS      current
    DESCRIPTION
        "Represents the list of station id which use semicolons to
         separate each station id."
    REFERENCE
        "Section 4.6.8. of CAPWAP Protocol Specification, RFC xxx."
    ::= { capwapBaseNotifyVarObjects 6 }

capwapBaseNtfAuthenFailureReason OBJECT-TYPE
    SYNTAX      INTEGER {
                  keyMismatch(1),
                  invalidCA(2),
                  micError(3),
                  timeout(4),
                  unknown(8)
                }
    MAX-ACCESS  accessible-for-notify
    STATUS      current
    DESCRIPTION
        "Represents reason for WTP authorization failure.
         The following enumerated values are supported:
           keyMismatch(1) - WTP's and AC's key is not matched,
           invalidCA(2)   - ca is not valid,
           micError(3)    - detect MIC error,
           timeout(4)     - WaitDTLS Timer is timeout,
           unknown(8)     - Unknown reason."
    REFERENCE
        "Section 2.3.1. of CAPWAP Protocol Specification, RFC xxx."
    ::= { capwapBaseNotifyVarObjects 7 }

capwapBaseNtfRadioOperStatusFlag OBJECT-TYPE
SYNTAX      INTEGER {
                  reserved(0),
                  operable(1),
                  inoperable(2)
                }
    MAX-ACCESS  accessible-for-notify
    STATUS      current
    DESCRIPTION
        "Represents the operation status of a radio.
         The following enumerated values are supported:
           reserved(0)   - Reserved
           operable(1)   - To indicate radio is operable,
           inoperable(2) - To indicate radio is inoperable, and
                           capwapBaseNtfRadioStatusCause object will
                           give reason in details."
    REFERENCE
        "Section 4.6.33. of CAPWAP Protocol Specification, RFC xxx."
    ::= { capwapBaseNotifyVarObjects 8 }

capwapBaseNtfRadioStatusCause OBJECT-TYPE
    SYNTAX      INTEGER {
                  normal(0),
                  hwError(1),
                  swError(2),
                  adminSet(3)
                }
    MAX-ACCESS  accessible-for-notify
    STATUS      current
    DESCRIPTION
        "Represents the reason the radio is out of service.
         The following enumerated values are supported:
           normal(0)   - Normal Status,
           hwError(1)  - Radio Failure,
           swError(2)  - Software Failure,
           adminSet(3) - Administratively Set."
    REFERENCE
        "Section 4.6.33. of CAPWAP Protocol Specification, RFC xxx."
    ::= { capwapBaseNotifyVarObjects 9 }

capwapBaseNtfJoinFailureReason  OBJECT-TYPE
    SYNTAX      INTEGER {
                  unspecified(1),
                  resDepletion(2),
                  unknownSource(3),
                  incorrectData(4),
                  sessionIdInUse(5),
                  notSupportHw(6),
                  notSupportBinding(7)
   }
    MAX-ACCESS  accessible-for-notify
    STATUS      current
    DESCRIPTION
        "Represents the reason of join failure.
         The following enumerated values are supported:
           unspecified(1)       - unspecified failure reason,
           resDepletion(2)      - Resource Depletion,
           unknownSource(3)     - Unknown Source,
           incorrectData(4)     - Incorrect Data,
           sessionIdInUse(5)    - Session ID already in use,
           notSupportHw(6)      - WTP Hardware not supported,
           notSupportBinding(7) - Binding Not Supported."
    REFERENCE
        "Section 4.6.34. of CAPWAP Protocol Specification, RFC xxx."
    ::= { capwapBaseNotifyVarObjects 10 }

capwapBaseNtfImageFailureReason  OBJECT-TYPE
    SYNTAX      INTEGER {
                  invalidChecksum(1),
                  invalidLength(2),
                  other(3),
                  inStorage(4)
                }
    MAX-ACCESS  accessible-for-notify
    STATUS      current
    DESCRIPTION
        "Represents the reason of image failure.
         The following enumerated values are supported:
           invalidChecksum(1) - Invalid Checksum,
           invalidLength(2)   - Invalid Data Length,
           other(3)           - Other Error,
           inStorage(4)       - Image Already Present."
    REFERENCE
        "Section 4.6.34. of CAPWAP Protocol Specification, RFC xxx."
    ::= { capwapBaseNotifyVarObjects 11 }

capwapBaseNtfConfigMsgErrorType  OBJECT-TYPE
    SYNTAX      INTEGER {
                  unknownElement(1),
                  unsupportedElement(2),
                  unknownValue(3),
                  unsupportedValue(4)
                }
    MAX-ACCESS  accessible-for-notify
    STATUS      current
    DESCRIPTION
        "Represents the type of configuration message error.
The following enumerated values are supported:
           unknownElement(1)     - Unknown Message Element,
           unsupportedElement(2) - Unsupported Message Element,
           unknownValue(3)       - Unknown Message Element Value,
           unsupportedValue(4)   - Unsupported Message Element Value."
    REFERENCE
        "Section 4.6.35. of CAPWAP Protocol Specification, RFC xxx."
   ::= { capwapBaseNotifyVarObjects 12 }

capwapBaseNtfMsgErrorElements  OBJECT-TYPE
    SYNTAX      SnmpAdminString
    MAX-ACCESS  accessible-for-notify
    STATUS      current
    DESCRIPTION
        "Represents the message elements sent by the AC in the
         Configuration Status Response message that caused the error."
    REFERENCE
        "Section 4.6.35. of CAPWAP Protocol Specification, RFC xxx."
    ::= { capwapBaseNotifyVarObjects 13 }

-- Module compliance

capwapBaseCompliances OBJECT IDENTIFIER
    ::= { capwapBaseConformance 1 }

capwapBaseGroups OBJECT IDENTIFIER
    ::= { capwapBaseConformance 2 }

capwapBaseCompliance MODULE-COMPLIANCE
   STATUS current
   DESCRIPTION
       "Describes the requirements for conformance to the
        CAPWAP-BASE-MIB."

   MODULE -- this module
     MANDATORY-GROUPS {
       capwapBaseAcNodeGroup,
       capwapBaseWtpStateGroup,
       capwapBaseWtpsGroup,
       capwapBaseRadiosGroup,
       capwapBaseStationsGroup
     }

     GROUP capwapBaseAcNodeGroup2
     DESCRIPTION
         "The capwapBaseAcNodeGroup2 group is optional."

     GROUP capwapBaseAcNameListGroup
DESCRIPTION
         "The capwapBaseAcNameListGroup group is optional."

     GROUP capwapBaseMacAclsGroup
     DESCRIPTION
         "The capwapBaseMacAclsGroup group is optional."

     GROUP capwapBaseWtpsGroup2
     DESCRIPTION
         "The capwapBaseWtpsGroup2 group is optional."

     GROUP capwapBaseWtpRebootStatsGroup
     DESCRIPTION
         "The capwapBaseWtpRebootStatsGroup group is optional."

     GROUP capwapBaseRadioStatsGroup
     DESCRIPTION
         "The capwapBaseRadioStatsGroup group is optional."

     GROUP capwapBaseParametersGroup
     DESCRIPTION
         "The capwapBaseParametersGroup group is optional."

     GROUP capwapBaseStatsGroup
     DESCRIPTION
         "The capwapBaseStatsGroup group is optional."

     GROUP capwapBaseNotificationGroup
     DESCRIPTION
          "The group capwapBaseNotificationGroup is optional."

     GROUP capwapBaseNotifyVarGroup
     DESCRIPTION
         "The capwapBaseNotifyVarGroup group is optional.
          If capwapBaseNotificationGroup is supported,
          this group must be implemented."

     OBJECT     capwapBaseRadioWirelessBinding
     SYNTAX     INTEGER { reserved0(0), reserved2(2) }
     DESCRIPTION
         "A value other than reserved0(0), reserved2(2) need not be
          supported if there is no wireless binding defined for
          technologies used."
     ::= { capwapBaseCompliances 1 }

capwapBaseAcNodeGroup    OBJECT-GROUP
    OBJECTS {
      capwapBaseWtpSessions,

 capwapBaseWtpSessionsLimit,
      capwapBaseStationSessions,
      capwapBaseStationSessionsLimit
    }
    STATUS  current
    DESCRIPTION
        "The collection of objects which are used to represent
         basic properties for AC from CAPWAP protocol perspective."
    ::= { capwapBaseGroups 1 }

capwapBaseAcNodeGroup2   OBJECT-GROUP
    OBJECTS {
      capwapBaseDataChannelSecOptions,
      capwapBaseDataChannelSecConfig,
      capwapBaseControlChannelAuthenOptions,
      capwapBaseControlChannelAuthenConfig
     }
    STATUS  current
    DESCRIPTION
        "The collection of objects which are used to represent
         other properties such as security for AC from
         CAPWAP protocol perspective."
    ::= { capwapBaseGroups 2 }

capwapBaseAcNameListGroup  OBJECT-GROUP
    OBJECTS {
      capwapBaseAcNameListName,
      capwapBaseAcNameListPriority,
      capwapBaseAcNameListRowStatus
    }
    STATUS  current
    DESCRIPTION
        "The collection of objects which are used to configure
         AC name list."
    ::= { capwapBaseGroups 3 }

capwapBaseMacAclsGroup  OBJECT-GROUP
    OBJECTS {
      capwapBaseMacAclStationId,
      capwapBaseMacAclRowStatus
    }
    STATUS  current
    DESCRIPTION
        "The collection of objects which are used to configure
         stations ACL."
    ::= { capwapBaseGroups 4 }

capwapBaseWtpStateGroup    OBJECT-GROUP
 OBJECTS {
      capwapBaseWtpIpAddressType,
      capwapBaseWtpIpAddress,
      capwapBaseWtpPhyAddress,
      capwapBaseWtpState
    }
    STATUS  current
    DESCRIPTION
        "The collection of objects which are used to represent
         WTP state information."
    ::= { capwapBaseGroups 5 }

capwapBaseWtpsGroup    OBJECT-GROUP
    OBJECTS {
      capwapBaseWtpName,
      capwapBaseWtpLocation,
      capwapBaseWtpBaseMacAddress,
      capwapBaseTunnelModeOptions,
      capwapBaseMacTypeOptions,
      capwapBaseWtpRadiosInUseNum,
      capwapBaseWtpRadioNumLimit
    }
    STATUS  current
    DESCRIPTION
        "The collection of objects which are used to represent
         configuration and properties information for WTP
         in running state."
    ::= { capwapBaseGroups 6 }

capwapBaseWtpsGroup2   OBJECT-GROUP
    OBJECTS {
      capwapBaseWtpPhyIndex,
      capwapBaseWtpDiscoveryType,
      capwapBaseWtpStaticIpEnable,
      capwapBaseWtpStaticIpType,
      capwapBaseWtpStaticIp,
      capwapBaseWtpNetmask,
      capwapBaseWtpGateway,
      capwapBaseWtpFallbackEnable,
      capwapBaseWtpRetransmitCount,
      capwapBaseWtpMaxDiscoveries,
      capwapBaseWtpMaxFailedDTLSSessionRetry,
      capwapBaseWtpMaxRetransmitCnt,
      capwapBaseWtpDataChannelKeepAliveTimer,
      capwapBaseWtpDataChannelDeadInterval,
      capwapBaseWtpDiscoveryInterval,
      capwapBaseWtpDTLSSessionDeleteTimer,
      capwapBaseWtpEchoInterval,
capwapBaseWtpIdleTimeout,
      capwapBaseWtpImageDataStartTimer,
      capwapBaseWtpMaxDiscoveryInterval,
      capwapBaseWtpReportInterval,
      capwapBaseWtpRetransmitInterval,
      capwapBaseWtpSilentInterval,
      capwapBaseWtpStatisticsTimer,
      capwapBaseWtpWaitDTLSTimer
    }
    STATUS  current
    DESCRIPTION
        "The collection of objects which are used to represent
         configuration and properties information for WTP
         in running state."
    ::= { capwapBaseGroups 7 }

capwapBaseRadiosGroup    OBJECT-GROUP
    OBJECTS {
      capwapBaseVirtualRadioIfIndex,
      capwapBaseRadioWirelessBinding
    }
    STATUS  current
    DESCRIPTION
        "The collection of objects which are used to represent
         wireless binding type, the mapping relationship between
         'WLAN Virtual Radio Interface' and PHY radio."
    ::= { capwapBaseGroups 8 }

capwapBaseStationsGroup    OBJECT-GROUP
    OBJECTS {
      capwapBaseStationAddedTime,
      capwapBaseStationVlanName
    }
    STATUS  current
    DESCRIPTION
        "The collection of objects which are used to represent
         stations' basic property."
    ::= { capwapBaseGroups 9 }

capwapBaseWtpRebootStatsGroup    OBJECT-GROUP
    OBJECTS {
      capwapBaseWtpRebootCount,
      capwapBaseWtpInitCount,
      capwapBaseWtpLinkFailureCount,
      capwapBaseWtpSwFailureCount,
      capwapBaseWtpHwFailureCount,
      capwapBaseWtpOtherFailureCount,
      capwapBaseWtpUnknownFailureCount,
 capwapBaseWtpLastFailureType
    }
    STATUS  current
    DESCRIPTION
        "The collection of objects which are used for collecting
         WTP reboot count, link failure count, hardware failure
         count and so on."
    ::= { capwapBaseGroups 10 }

capwapBaseRadioStatsGroup    OBJECT-GROUP
    OBJECTS {
      capwapBaseRadioResetCount,
      capwapBaseRadioSwFailCount,
      capwapBaseRadioHwFailCount,
      capwapBaseRadioOtherFailCount,
      capwapBaseRadioUnknownFailCount,
      capwapBaseRadioConfigUpdateCount,
      capwapBaseRadioChannelChangeCount,
      capwapBaseRadioBandChangeCount,
      capwapBaseRadioCurrentNoiseFloor,
      capwapBaseRadioDecryptErrorCount,
      capwapBaseRadioLastFailType
    }
    STATUS  current
    DESCRIPTION
        "The collection of objects which are used for collecting
         radio reset count, channel change count, hardware failure
         count and so on"
    ::= { capwapBaseGroups 11 }

capwapBaseParametersGroup    OBJECT-GROUP
    OBJECTS {
      capwapBaseAcMaxRetransmitCnt,
      capwapBaseAcChangeStatePendingTimer,
      capwapBaseAcDataCheckTimer,
      capwapBaseAcDTLSSessionDeleteTimer,
      capwapBaseAcEchoInterval,
      capwapBaseAcRetransmitInterval,
      capwapBaseAcSilentInterval,
      capwapBaseAcWaitDTLSTimer,
      capwapBaseAcWaitJoinTimer
    }
    STATUS  current
    DESCRIPTION
        "Objects used for CAPWAP protocol."
    ::= { capwapBaseGroups 12 }

capwapBaseStatsGroup    OBJECT-GROUP

OBJECTS {
      capwapBaseFailedDTLSAuthFailCount,
      capwapBaseFailedDTLSSessionCount
    }
    STATUS  current
    DESCRIPTION
        "Objects used for CAPWAP protocol."
    ::= { capwapBaseGroups 13 }

capwapBaseNotificationGroup    NOTIFICATION-GROUP
    NOTIFICATIONS {
      capwapBaseChannelUp,
      capwapBaseChannelDown,
      capwapBaseDecryptErrorReport,
      capwapBaseJoinFailure,
      capwapBaseImageUpgradeFailure,
      capwapBaseConfigMsgError,
      capwapBaseRadioOperableStatus,
      capwapBaseAuthenticationFailure
    }
    STATUS  current
    DESCRIPTION
        "Collection of notifications in this MIB."
    ::= { capwapBaseGroups 14 }

capwapBaseNotifyVarGroup    OBJECT-GROUP
    OBJECTS {
      capwapBaseNtfWtpId,
      capwapBaseNtfRadioId,
      capwapBaseNtfChannelType,
      capwapBaseNtfAuthenMethod,
      capwapBaseNtfChannelDownReason,
      capwapBaseNtfStationIdList,
      capwapBaseNtfAuthenFailureReason,
      capwapBaseNtfRadioOperStatusFlag,
      capwapBaseNtfRadioStatusCause,
      capwapBaseNtfJoinFailureReason,
      capwapBaseNtfImageFailureReason,
      capwapBaseNtfConfigMsgErrorType,
      capwapBaseNtfMsgErrorElements
    }
    STATUS  current
    DESCRIPTION
        "Objects used for notification."
    ::= { capwapBaseGroups 15 }

END
