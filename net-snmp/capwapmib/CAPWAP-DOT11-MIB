CAPWAP-DOT11-MIB DEFINITIONS ::= BEGIN
IMPORTS
RowStatus, TEXTUAL-CONVENTION
FROM SNMPv2-TC
OBJECT-GROUP, MODULE-COMPLIANCE
FROM SNMPv2-CONF
MODULE-IDENTITY, OBJECT-TYPE, mib-2, Unsigned32
FROM SNMPv2-SMI

ifIndex, InterfaceIndex
FROM IF-MIB
CapwapBaseMacTypeTC, CapwapBaseTunnelModeTC
FROM CAPWAP-BASE-MIB;
capwapDot11MIB MODULE-IDENTITY
LAST-UPDATED "200810270000Z" -- Oct 27th, 2008
ORGANIZATION "IETF Control And Provisioning of Wireless Access
Points (CAPWAP) Working Group
http://www.ietf.org/html.charters/capwap-charter.html"
CONTACT-INFO
"General Discussion: capwap@frascone.com
To Subscribe: http://lists.frascone.com/mailman/listinfo/capwap
Yang Shi
H3C, Digital Technology Plaza, NO.9 Shangdi 9th Street,Haidian
District,Beijing,China(100085)
Email: young@h3c.com
David T. Perkins
228 Bayview Dr
San Carlos, CA 94070
USA
Phone: +1 408 394-8702
Email: dperkins@snmpinfo.com
Chris Elliott
Cisco Systems, Inc.
7025 Kit Creek Rd., P.O. Box 14987
Research Triangle Park 27709
USA
Phone: +1 919-392-2146
Email: chelliot@cisco.com
Yong Zhang
Fortinet, Inc.
1090 Kifer Road
Sunnyvale, CA 94086
USA
Email: yzhang@fortinet.com"
DESCRIPTION
"Copyright (C) 2008 The Internet Society. This version of
the MIB module is part of RFC xxx; see the RFC itself
for full legal notices.
This MIB module contains managed object definitions for
the IEEE 802.11 bindings for the CAPWAP Protocol."

REVISION "200810270000Z"
DESCRIPTION
"Initial version, published as RFC xxx"
::= { mib-2 0 }
-- Textual conventions
CapwapDot11WlanIdTC ::= TEXTUAL-CONVENTION
DISPLAY-HINT "d"
STATUS current
DESCRIPTION
"Represents an unique identifier of a WLAN."
SYNTAX Unsigned32 (1..16)
-- Top level components of this MIB
-- Tables, Scalars
capwapDot11Objects OBJECT IDENTIFIER
::= { capwapDot11MIB 1 }
-- Conformance
capwapDot11Conformance OBJECT IDENTIFIER
::= { capwapDot11MIB 2 }
-- capwapDot11WlanConfigTable Table
capwapDot11WlanConfigTable OBJECT-TYPE
SYNTAX SEQUENCE OF CapwapDot11WlanConfigEntry
MAX-ACCESS not-accessible
STATUS current
DESCRIPTION
"A table of objects that display and control the WLAN
service.
Values of all read-create objects in this
table are persistent at restart/reboot."
::= { capwapDot11Objects 1 }
capwapDot11WlanConfigEntry OBJECT-TYPE
SYNTAX CapwapDot11WlanConfigEntry
MAX-ACCESS not-accessible
STATUS current
DESCRIPTION
"A set of objects that display and control the WLAN
service."
INDEX { capwapDot11WlanId }
::= { capwapDot11WlanConfigTable 1 }


CapwapDot11WlanConfigEntry ::=
SEQUENCE {
capwapDot11WlanId CapwapDot11WlanIdTC,
capwapDot11WlanServiceIfIndex InterfaceIndex,
capwapDot11WlanMacType CapwapBaseMacTypeTC,
capwapDot11WlanTunnelMode CapwapBaseTunnelModeTC,
capwapDot11WlanConfigRowStatus RowStatus
}
capwapDot11WlanId OBJECT-TYPE
SYNTAX CapwapDot11WlanIdTC
MAX-ACCESS not-accessible
STATUS current
DESCRIPTION
"Represents the WLAN Id for a WLAN which has a
capwapDot11WlanServiceIfIndex interface corresponding to it."
REFERENCE
"Section 6.1. of CAPWAP Protocol Binding for IEEE 802.11,
RFC xxx."
::= { capwapDot11WlanConfigEntry 1 }
capwapDot11WlanServiceIfIndex OBJECT-TYPE
SYNTAX InterfaceIndex
MAX-ACCESS read-only
STATUS current
DESCRIPTION
"Represents the index value that uniquely identifies a
’WLAN Service Interface’. The interface identified by a
particular value of this index is the same interface as
identified by the same value of ifIndex.
Before WTPs connect to AC and get configuration, administrator
will prepare configuration for them. For a specific WLAN
service, a logical interface of ’WLAN Service Interface’
ifType will be created, and administrator could configure WLAN
parameter through it. For example, according to IEEE 802.11
’6.1. IEEE 802.11 Add WLAN’ in the
[I-D.ietf-capwap-protocol-binding-ieee80211], administrator
could configure Auth Type for a WLAN. The ’WLAN
Service Interface’ provides a way to uniquely identify each
WLAN by logical on the AC. As most MIBs use ifIndex to
identify an interface for configuration and statistic data,
for example, dot11AuthenticationAlgorithmsTable in IEEE 802.11
MIB use ifIndex as index, and dot11AuthenticationAlgorithm
object is for Auth Type mentioned in the CAPWAP ’6.1. IEEE
802.11 Add WLAN’, With the way of ’WLAN Service Interface’,
it will easily reuse MIB table like
dot11AuthenticationAlgorithmsTable, while only care for other
configurations like capwapDot11WlanTunnelMode."

::= { capwapDot11WlanConfigEntry 2 }
capwapDot11WlanMacType OBJECT-TYPE
SYNTAX CapwapBaseMacTypeTC
MAX-ACCESS read-create
STATUS current
DESCRIPTION
"Represents whether the WTP should support the WLAN in
Local or Split MAC modes."
REFERENCE
"Section 6.1. of CAPWAP Protocol Binding for IEEE 802.11,
RFC xxx."
::= { capwapDot11WlanConfigEntry 3 }
capwapDot11WlanTunnelMode OBJECT-TYPE
SYNTAX CapwapBaseTunnelModeTC
MAX-ACCESS read-create
STATUS current
DESCRIPTION
"Represents the frame tunneling type to be used for 802.11 data
frames from all stations associated with the WLAN.
Bits are exclusive with each other for a specific WLAN Id."
REFERENCE
"Section 6.1. of CAPWAP Protocol Binding for IEEE 802.11,
RFC xxx."
::= { capwapDot11WlanConfigEntry 4 }
capwapDot11WlanConfigRowStatus OBJECT-TYPE
SYNTAX RowStatus
MAX-ACCESS read-create
STATUS current
DESCRIPTION
"This variable is used to create, modify, and/or delete a row in
this table."
::= { capwapDot11WlanConfigEntry 5 }
-- End of capwapDot11WlanConfigTable Table
-- capwapDot11WlanBindTable Table
capwapDot11WlanBindTable OBJECT-TYPE
SYNTAX SEQUENCE OF CapwapDot11WlanBindEntry
MAX-ACCESS not-accessible
STATUS current
DESCRIPTION
"A table of objects that display and control the mapping
relationship between interface of ’WTP Virtual Radio Interface’

interface and interface of ’WLAN BSS Interface’.
The PHY address for interface of ’WTP Virtual Radio
Interface’ ifType will be base BSSID address for PHY
radio."
REFERENCE
"Section 6.1. of CAPWAP Protocol Binding for IEEE 802.11,
RFC xxx."
::= { capwapDot11Objects 2 }
capwapDot11WlanBindEntry OBJECT-TYPE
SYNTAX CapwapDot11WlanBindEntry
MAX-ACCESS not-accessible
STATUS current
DESCRIPTION
"A set of objects that display the mapping relationship
between interface of ’WTP Virtual Radio Interface’ and
interface of ’WLAN BSS Interface’."
INDEX { ifIndex, capwapDot11WlanId }
::= { capwapDot11WlanBindTable 1 }
CapwapDot11WlanBindEntry ::=
SEQUENCE {
capwapDot11WlanBssIfIndex InterfaceIndex,
capwapDot11WlanBssRowStatus RowStatus
}
capwapDot11WlanBssIfIndex OBJECT-TYPE
SYNTAX InterfaceIndex
MAX-ACCESS read-only
STATUS current
DESCRIPTION
"Represents the index value that uniquely identifies a
’WLAN BSS Interface’. The interface identified by a
particular value of this index is the same interface as
identified by the same value of ifIndex.
Each capwapDot11WlanBssIfIndex will corresponding to a
WLAN service on the PHY radio which is identified by ifIndex.
The PHY address for capwapDot11WlanBssIfIndex is BSSID.
While manufacturers are free to assign BSSIDs using any
arbitrary mechanism, it is advised that where possible the
BSSIDs are assigned as a contiguous block.
When assigned as a block, implementations can still assign
any of the available BSSIDs to any WLAN. One possible method
is for the WTP to assign the address using the following
algorithm: base BSSID address + WLAN ID."
REFERENCE
"Section 2.4. of CAPWAP Protocol Binding for IEEE 802.11,
RFC xxx."

::= { capwapDot11WlanBindEntry 1 }
capwapDot11WlanBssRowStatus OBJECT-TYPE
SYNTAX RowStatus
MAX-ACCESS read-create
STATUS current
DESCRIPTION
"This variable is used to create, modify, and/or delete a row
in this table."
::= { capwapDot11WlanBindEntry 2 }
-- End of capwapDot11WlanBindTable Table
-- Module compliance
capwapDot11Groups OBJECT IDENTIFIER
::= { capwapDot11Conformance 1 }
capwapDot11Compliances OBJECT IDENTIFIER
::= { capwapDot11Conformance 2 }
capwapDot11Compliance MODULE-COMPLIANCE
STATUS current
DESCRIPTION
"Describes the requirements for conformance to the
CAPWAP-DOT11-MIB."
MODULE -- this module
MANDATORY-GROUPS {
capwapDot11WlanConfigGroup,
capwapDot11WlanBindGroup
}
::= { capwapDot11Compliances 1 }
capwapDot11WlanConfigGroup OBJECT-GROUP
OBJECTS {
capwapDot11WlanServiceIfIndex,
capwapDot11WlanMacType,
capwapDot11WlanTunnelMode,
capwapDot11WlanConfigRowStatus
}
STATUS current
DESCRIPTION
"The collection of objects which are used to configure
property of WLAN."
::= { capwapDot11Groups 1 }

capwapDot11WlanBindGroup OBJECT-GROUP
OBJECTS {
capwapDot11WlanBssIfIndex,
capwapDot11WlanBssRowStatus
}
STATUS current
DESCRIPTION
"The collection of objects which are used to configure
WLAN BSS."
::= { capwapDot11Groups 2 }
END
